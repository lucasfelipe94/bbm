-- ============================================================================
-- Copyright (c) 2010-2016 Hewlett-Packard Development Company, L.P.
-- Description: This MIB describes OID of HPN products.
--
-- Reference:
-- Version: V1.03
-- History:
--   V1.00 2013-01-16 Created by songhao
--   V1.01 2013-10-09  by songhao
--      Added OID 11 to 16 under hpnWireless
--   V1.02 2015-04-18  by songhao
--      Added OID 17 to 27 under hpnWireless
--   V1.03 2016-04-02  by songhao
--      Added OID 28 to 29 under hpnWireless
--      Modified name of 17, 18 under hpnWireless
-- ============================================================================
HPN-ICF-PRODUCT-ID-MIB DEFINITIONS ::= BEGIN
    IMPORTS
        nm
            FROM HPN-ICF-OID-MIB;

-- Objects under .enterprises.hp(11).nm(2)
hpSystem         OBJECT IDENTIFIER ::= { nm 3 }
netElement       OBJECT IDENTIFIER ::= { hpSystem 7 }
hpn              OBJECT IDENTIFIER ::= { netElement 15 }
hpnProducts      OBJECT IDENTIFIER ::= { hpn 1 }

-- Objects under .enterprises.hp(11).nm(2).hpSystem(3).netElement(7).hpn(15).hpnProducts(1)
hpnSwitch        OBJECT IDENTIFIER ::= { hpnProducts 1 }
hpnRouter        OBJECT IDENTIFIER ::= { hpnProducts 2 }
hpnWireless      OBJECT IDENTIFIER ::= { hpnProducts 3 }
hpnSecurity      OBJECT IDENTIFIER ::= { hpnProducts 4 }

-- Objects under .enterprises.hp(11).nm(2).hpSystem(3).netElement(7).hpn(15).hpnProducts(1).hpnWireless(3)
hpnLSU3WCMD0                    OBJECT IDENTIFIER ::= { hpnWireless 1 }
hpn83024P                       OBJECT IDENTIFIER ::= { hpnWireless 2 }
hpn83024PLSW                    OBJECT IDENTIFIER ::= { hpnWireless 3 }
hpn8308P                        OBJECT IDENTIFIER ::= { hpnWireless 4 }
hpn8308PLSW                     OBJECT IDENTIFIER ::= { hpnWireless 5 }
hpnLSU3WCMD0TAA                 OBJECT IDENTIFIER ::= { hpnWireless 6 }
hpn83024PTAA                    OBJECT IDENTIFIER ::= { hpnWireless 7 }
hpn83024PTAALSW                 OBJECT IDENTIFIER ::= { hpnWireless 8 }
hpn8308PTAA                     OBJECT IDENTIFIER ::= { hpnWireless 9 }
hpn8308PTAALSW                  OBJECT IDENTIFIER ::= { hpnWireless 10 }
hpn870WCM                       OBJECT IDENTIFIER ::= { hpnWireless 11 }
hpn870LSW                       OBJECT IDENTIFIER ::= { hpnWireless 12 }
hpn850                          OBJECT IDENTIFIER ::= { hpnWireless 13 }
hpn870TAAWCM                    OBJECT IDENTIFIER ::= { hpnWireless 14 }
hpn870TAALSW                    OBJECT IDENTIFIER ::= { hpnWireless 15 }
hpn850TAA                       OBJECT IDENTIFIER ::= { hpnWireless 16 }
hpnLSU3WCMD0V7                  OBJECT IDENTIFIER ::= { hpnWireless 17 }
hpnLSU3WCMD0TAAV7               OBJECT IDENTIFIER ::= { hpnWireless 18 }
hpn870V7                        OBJECT IDENTIFIER ::= { hpnWireless 19 }
hpn850V7                        OBJECT IDENTIFIER ::= { hpnWireless 20 }
hpn870TAAV7                     OBJECT IDENTIFIER ::= { hpnWireless 21 }
hpn850TAAV7                     OBJECT IDENTIFIER ::= { hpnWireless 22 }
hpnVAP                          OBJECT IDENTIFIER ::= { hpnWireless 23 }
hpn8308PV7                      OBJECT IDENTIFIER ::= { hpnWireless 24 }
hpn83024PV7                     OBJECT IDENTIFIER ::= { hpnWireless 25 }
hpn8308PTAAV7                   OBJECT IDENTIFIER ::= { hpnWireless 26 }
hpn83024PTAAV7                  OBJECT IDENTIFIER ::= { hpnWireless 27 }
hpn890                          OBJECT IDENTIFIER ::= { hpnWireless 28 }
hpn890TAA                       OBJECT IDENTIFIER ::= { hpnWireless 29 }

END
