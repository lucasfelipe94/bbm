-- =================================================================
-- Copyright (c) 2010-2016 Hewlett-Packard Development Company, L.P.
--
-- Description: This MIB is to provide the definition of the POSA
--              (Point Of Sale Access) system.
-- Reference:
-- Version: V1.9
-- History:
-- V1.0 2008-03-12 Initial version, created by Lei Hao, Yang Xu
-- V1.1 2008-09-22 updated by yangxu
--      Modified the limitation(SIZE (4..7)) of hpnicfPosaMapDestCode
--      Modified the default value of hpnicfPosaFcmAnswerTimeout
--      Modified the limitation(0..65535) of hpnicfPosaAppHostPort
--      Modified the limitation(0..65535) of hpnicfPosaTerminalListenPort
--      Added new node hpnicfPosaTerminalTransAppID in hpnicfPosaTerminalTable
--      Renamed hpnicfPosaAppDiscardedPkts to hpnicfPosaAppInDiscardedPkts
--      Added new node hpnicfPosaAppOutDiscardedPkts in hpnicfPosaAppStatTable
--      Renamed hpnicfPosaTerminalDiscardedPkts to hpnicfPosaTerminalInDiscardedPkts
--      Added new node hpnicfPosaTerminalOutDiscardedPkts in hpnicfPosaTerminalStatTable
--      Modified the description of object hpnicfPosaAppHostPort,
--      hpnicfPosaFcmStatTimeoutCnts, hpnicfPosaFcmStatConnectFailCnts,
--      hpnicfPosaAppRecvPkts, hpnicfPosaAppSendPkts, hpnicfPosaAppErrPkts,
--      hpnicfPosaAppDistributeErrCnts, hpnicfPosaAppInDiscardedPkts,
--      hpnicfPosaTerminalRecvPkts, hpnicfPosaTerminalSendPkts,
--      hpnicfPosaTerminalErrPkts, hpnicfPosaTerminalMapErrCnts,
--      hpnicfPosaTerminalInDiscardedPkts.
-- V1.2 2010-04-08 updated by Cai Zibin, Tong Wei
--      Added hpnicfPosaFcmConfTable
--      Added hpnicfPosaTcpTermStatTable
--      Added hpnicfPosaBatchTerminalTable
--      Added hpnicfPosaCallerStatTable
--      Added new node hpnicfPosaTerminalHangUp, hpnicfPosaFcmLinkNegoFailed,
--      hpnicfPosaFcmPhyNegoFailed in hpnicfPosaTrapPrex
--      Added new node hpnicfPosaSrvStateChangeTrapEnable,
--      hpnicfPosaAppStateChangeTrapEnable, hpnicfPosaTerminalHangUpTrapEnable,
--      hpnicfPosaFcmLnkNegoFailTrapEnable, hpnicfPosaFcmPhyNegoFailTrapEnable,
--      in hpnicfPosaControl
--      hpnicfPosaAppName, hpnicfPosaCallerIDTransEnable, hpnicfPosaTpduChangeStrategy
--      in hpnicfPosaAppTable
--      hpnicfPosaTerminalName and hpnicfPosaTerminalCfgIfIndex in hpnicfPosaTerminalTable
--      hpnicfPosaMapSrcCode in hpnicfPosaMapTable
-- V1.3 2011-09-01 updated by he changfu,du pengfei
--      Added new node hpnicfPosaBackupAppID,hpnicfPosaQuietTimeOut
--      in hpnicfPosaAppTable
--      Added a new value for HpnicfPeerState.
--      2011-12-12 updated by lei hao,yang xu
--      Added new node, hpnicfPosaFcmStatTransCnts, hpnicfPosaFcmStatTransSuccessCnts
--      and hpnicfPosaFcmStatTransCntsClear in hpnicfPosaFcmStatTable
--      2012-2-28 updated by zhangxianyi
--      Added new node hpnicfPosaAppHello, hpnicfPosaAppHelloInterval
--      hpnicfPosaAppRouterPort
--      in hpnicfPosaAppTable
-- V1.4 2012-8-22 updated by dupengfei
--      Added value of "error(9)" for HpnicfPeerState
-- V1.5 2013-08-30 updated by q04356
--      Modified the range of hpnicfPosaAppID and hpnicfPosaBackupAppID in hpnicfPosaAppTable
--      Modified the range of hpnicfPosaTerminalTransAppID in hpnicfPosaTerminalTable
--      Modified the range of hpnicfPosaMapAppID in hpnicfPosaMapTable
--      2013-09-03 updated by q04356
--      Added new nodes hpnicfPosaTcpConnectionNumber, hpnicfPosaFcmConnectionNumber
--      hpnicfPosaTcpConnectionThreshold, hpnicfPosaFcmConnectionThreshold,
--      hpnicfPosaTcpConnectionTrapEnable and
--      hpnicfPosaFcmConnectionTrapEnable in hpnicfPosaControl
--      Added new nodes hpnicfPosaTcpConnectionExceed and
--      hpnicfPosaFcmConnectionExceed in hpnicfPosaTrapPrex
-- V1.6 2013-10-18 updated by zhangxinhua
--      Modified the MAX-ACCESS of hpnicfPosaTerminalID to be accessible-for-notify
--      Deleted the range description of hpnicfPosaTcpConnectionThreshold and
--      hpnicfPosaFcmConnectionThreshold
--      Added new nodes hpnicfPosaTcpTradeLimit, hpnicfPosaTcpTradeTrapEnable,
--      hpnicfPosaTcpTradeTimeout in hpnicfPosaControl
--      Added new nodes hpnicfPosaTcpTradeExceed in hpnicfPosaTrapPrex
--      2013-12-14 updated by q04356
--      Modified the default of hpnicfPosaFcmIdleTimeout in hpnicfPosaControl
-- V1.7 2014-05-29 updated by liubo
--      Modified the range for hpnicfPosaAppID and hpnicfPosaBackupAppID in hpnicfPosaAppTable
--      Modified the range for hpnicfPosaTerminalTransAppID in hpnicfPosaTerminalTable
--      Modified the range for hpnicfPosaMapAppID in hpnicfPosaMapTable
-- V1.8 2014-11-14 updated by liubo
--      Modified the range for hpnicfPosaTerminalID in hpnicfPosaTerminalTable
--      Modified the range for hpnicfPosaBatchTerminalFirstID in hpnicfPosaBatchTerminalTable
--      Modified the default value for hpnicfPosaFcmConnectionThreshold
-- V1.9 2015-8-26 updated by limeng
--      Added hpnicfPosaNiiStatTable
--      Added hpnicfPosaE1StatTable
--      Added new nodes hpnicfPosaTradeSuccessFallingTrapEnable, hpnicfPosaTradeSuccessFallingThreshold,
--      hpnicfPosaE1DialFallingTrapEnable, hpnicfPosaE1DialFallingThreshold
--      and hpnicfPosaFcmTradeAbnormalTrapEnable in hpnicfPosaControl
--      Added new node hpnicfPosaTermianlTcpConnectionNumber in hpnicfPosaTerminalStatTable
--      Added new nodes hpnicfPosaTradeSuccessFalling, hpnicfPosaE1DialFalling
--      and hpnicfPosaFcmTradeAbnormal in hpnicfPosaTrapPrex
--      Added new object hpnicfPosaCallerStatCallerID to hpnicfPosaTerminalHangUp
--      Added new object hpnicfPosaCallerStatCallerID to hpnicfPosaFcmLinkNegoFailed
--      Added new object hpnicfPosaCallerStatCallerID to hpnicfPosaFcmPhyNegoFailed
--      Modified the MAX-ACCESS of hpnicfPosaCallerStatCallerID to be accessible-for-notify
-- =================================================================
HPN-ICF-POSA-MIB DEFINITIONS ::= BEGIN

IMPORTS
    hpnicfCommon
        FROM HPN-ICF-OID-MIB
    Integer32, Counter32, OBJECT-TYPE, MODULE-IDENTITY, NOTIFICATION-TYPE,
    Counter64, Gauge32
        FROM SNMPv2-SMI
    RowStatus, TruthValue, TEXTUAL-CONVENTION
        FROM SNMPv2-TC
    InetAddress, InetAddressType
        FROM INET-ADDRESS-MIB
    ifIndex, ifDescr
        FROM IF-MIB;

hpnicfPosa MODULE-IDENTITY
    LAST-UPDATED "201508260000Z"
    ORGANIZATION
        ""
    CONTACT-INFO
        ""
    DESCRIPTION
        "This MIB is to provide the definition of the POSA
        (Point Of Sale Access) system."
    REVISION "201508260000Z"
    DESCRIPTION
        "Added hpnicfPosaNiiStatTable.
        Added hpnicfPosaE1StatTable.
        Added new nodes hpnicfPosaTradeSuccessFallingTrapEnable, hpnicfPosaTradeSuccessFallingThreshold,
        hpnicfPosaE1DialFallingTrapEnable, hpnicfPosaE1DialFallingThreshold
        and hpnicfPosaFcmTradeAbnormalTrapEnable in hpnicfPosaContro.
        Added new node hpnicfPosaTermianlTcpConnectionNumber in hpnicfPosaTerminalStatTable.
        Added new nodes hpnicfPosaTradeSuccessFalling, hpnicfPosaE1DialFalling
        and hpnicfPosaFcmTradeAbnormal in hpnicfPosaTrapPrex.
        Added new object hpnicfPosaCallerStatCallerID to hpnicfPosaTerminalHangUp.
        Added new object hpnicfPosaCallerStatCallerID to hpnicfPosaFcmLinkNegoFailed.
        Added new object hpnicfPosaCallerStatCallerID to hpnicfPosaFcmPhyNegoFailed.
        Modified the MAX-ACCESS of hpnicfPosaCallerStatCallerID to be accessible-for-notify."
    REVISION "201411140000Z"
    DESCRIPTION
        "Modified the range for hpnicfPosaTerminalID in hpnicfPosaTerminalTable.
        Modified the range for hpnicfPosaBatchTerminalFirstID in hpnicfPosaBatchTerminalTable.
        Modified the default value for hpnicfPosaFcmConnectionThreshold"
    REVISION "200803120933Z"
    DESCRIPTION
        "The initial revision of this MIB module."
    ::= { hpnicfCommon 92 }


-- definition of textual conventions

HpnicfAppServiceType ::= TEXTUAL-CONVENTION
    STATUS       current
    DESCRIPTION
        "The service type of a POS application.  It means the way
        in which the router connects with the application server.
        At present, it supports two service types, tcp(1) and flow(2).
        If the router connects with the server through SEARIAL/ASYNC
        interface, the service type is flow(1).  If through TCP/IP,
        the service type is tcp(1)."
    SYNTAX INTEGER
        {
        tcp(1),
        flow(2)
        }

HpnicfAppMode ::= TEXTUAL-CONVENTION
    STATUS       current
    DESCRIPTION
        "The work mode of a POS application.  It has two value normal(1)
        and temporary(2).  This attribute is valid only when the service type
        is tcp(1).  If it works in temporary(2) mode, the TCP connection
        between router and application server is established
        when a POS trade begins and disconnected when a POS trade finishes.
        In normal(1) mode, the TCP connection is established
        when POS function is enabled and exists all along."
    SYNTAX INTEGER
        {
        normal(1),
        temporary(2)
        }

HpnicfPeerState ::= TEXTUAL-CONVENTION
    STATUS       current
    DESCRIPTION
        "The current running state of the peer (application server or POS terminal)
        of the router.
        notset(1)     The peer is not configured correctly.
        down(2)       The interface connecting with the peer is down.
        up(3)         The interface connecting with the peer is up.
        kept(4)       The connection between router and the peer is
                      not established.
        linking(5)    The connection between router and the peer is
                      establishing.
        linked(6)     The connection between router and the peer is
                      established.
        multilink(7)  There are multiple connections between router and the peer.
        blocked(8)    The connection between router and the peer is
                      unreachable.
        error(9)      Enable failed.

        The status of down(2) and up(3) appear only when the router and the peer
        are connected with interface.
        The status about TCP connections appear when the router and the peer are
        connected with TCP/IP.
        "
    SYNTAX INTEGER
        {
        notset(1),
        down(2),
        up(3),
        kept(4),
        linking(5),
        linked(6),
        multilink(7),
        blocked(8),
        error(9)
        }

HpnicfTerminalAccessType ::= TEXTUAL-CONVENTION
    STATUS       current
    DESCRIPTION
        "The access type of a POS terminal.  Now it supports 3 types.
        fcm(1)  The POS terminal connects with router through FCM interface.
        flow(2) The POS terminal connects with router through SERIAL, ASYNC,
                AM (Analog Modem) or AUX interface.
        tcp(3)  The POS terminal connects with router through TCP/IP protocol.
                The default access type is fcm(2)."
    SYNTAX INTEGER
        {
        fcm(1),
        flow(2),
        tcp(3)
        }

HpnicfTpduChangeStrategy ::= TEXTUAL-CONVENTION
    STATUS       current
    DESCRIPTION
        "The strategy to modify the address of the packet from terminals before
        delivering it to application server.  Now it supports 2 types.
        ChangeTpduSrc(1)  Replace the source address of the packet with POSID.
        ChangeTpduDest(2) Replace the destination address of the packet with
                          POSID."
    SYNTAX INTEGER
        {
        changeTpduSrc(1),
        changeTpduDest(2)
        }

--
-- nodes defined
--

hpnicfPosaControl OBJECT IDENTIFIER ::= { hpnicfPosa 1 }

hpnicfPosaServerEnable OBJECT-TYPE
    SYNTAX INTEGER
        {
        disabled(1),
        enabled(2)
        }
    MAX-ACCESS read-write
    STATUS current
    DESCRIPTION
        "This attribute controls the starting or stoppage of POS access function.
        The defalut value is disabled(1)."
    DEFVAL { disabled }
    ::= { hpnicfPosaControl 1 }

hpnicfPosaFcmAnswerTimeout OBJECT-TYPE
    SYNTAX Integer32 (500..2000)
    UNITS "milliseconds"
    MAX-ACCESS read-write
    STATUS current
    DESCRIPTION
        "The maximum answer time of a POS connection through a FCM (Fast
        Connection Modem) interface.
        The answer time is the interval from the POS terminal sending request
        to the Router giving its reply, in units of milliseconds."
    DEFVAL { 2000 }
    ::= { hpnicfPosaControl 2 }

hpnicfPosaFcmTradeTimeout OBJECT-TYPE
    SYNTAX Integer32 (30000..12000000)
    UNITS "milliseconds"
    MAX-ACCESS read-write
    STATUS current
    DESCRIPTION
        "The maximum time of a POS trade through a FCM interface,
        in units of milliseconds."
    DEFVAL { 12000000 }
    ::= { hpnicfPosaControl 3 }

hpnicfPosaFcmIdleTimeout OBJECT-TYPE
    SYNTAX Integer32 (1..12000)
    UNITS "seconds"
    MAX-ACCESS read-write
    STATUS current
    DESCRIPTION
        "The maximum idle time of a POS connection through the FCM interface,
        in units of seconds."
    DEFVAL { 180 }
    ::= { hpnicfPosaControl 4 }

hpnicfPosaSrvStateChangeTrapEnable OBJECT-TYPE
    SYNTAX TruthValue
    MAX-ACCESS read-write
    STATUS current
    DESCRIPTION
        "This attribute controls whether the hpnicfPosaServerStatusChange trap will
        be sent or not."
    DEFVAL { true }
    ::= { hpnicfPosaControl 5 }

hpnicfPosaAppStateChangeTrapEnable OBJECT-TYPE
    SYNTAX TruthValue
    MAX-ACCESS read-write
    STATUS current
    DESCRIPTION
        "This attribute controls whether the hpnicfPosaAppStateChange trap will
        be sent or not."
    DEFVAL { true }
    ::= { hpnicfPosaControl 6 }

hpnicfPosaTerminalHangUpTrapEnable OBJECT-TYPE
    SYNTAX TruthValue
    MAX-ACCESS read-write
    STATUS current
    DESCRIPTION
        "This attribute controls whether the hpnicfPosaTerminalHangUp trap will
        be sent or not."
    DEFVAL { true }
    ::= { hpnicfPosaControl 7 }

hpnicfPosaFcmLnkNegoFailTrapEnable OBJECT-TYPE
    SYNTAX TruthValue
    MAX-ACCESS read-write
    STATUS current
    DESCRIPTION
        "This attribute controls whether the hpnicfPosaFcmLinkNegoFailed trap will
        be sent or not."
    DEFVAL { true }
    ::= { hpnicfPosaControl 8 }

hpnicfPosaFcmPhyNegoFailTrapEnable OBJECT-TYPE
    SYNTAX TruthValue
    MAX-ACCESS read-write
    STATUS current
    DESCRIPTION
        "This attribute controls whether the hpnicfPosaFcmPhyNegoFailed trap will
        be sent or not."
    DEFVAL { true }
    ::= { hpnicfPosaControl 9 }

hpnicfPosaTcpConnectionNumber OBJECT-TYPE
    SYNTAX Integer32
    MAX-ACCESS read-only
    STATUS current
    DESCRIPTION
        "The current number of TCP connections."
    ::= { hpnicfPosaControl 10 }

hpnicfPosaFcmConnectionNumber OBJECT-TYPE
    SYNTAX Integer32
    MAX-ACCESS read-only
    STATUS current
    DESCRIPTION
        "The current number of FCM connections."
    ::= { hpnicfPosaControl 11 }

hpnicfPosaTcpConnectionThreshold OBJECT-TYPE
    SYNTAX Integer32
    MAX-ACCESS read-write
    STATUS current
    DESCRIPTION
        "The threshold of TCP connections."
    DEFVAL {4096}
    ::= { hpnicfPosaControl 12 }

hpnicfPosaFcmConnectionThreshold OBJECT-TYPE
    SYNTAX Integer32
    MAX-ACCESS read-write
    STATUS current
    DESCRIPTION
        "The threshold of FCM connections."
    DEFVAL {1024}
    ::= { hpnicfPosaControl 13 }

hpnicfPosaTcpConnectionTrapEnable OBJECT-TYPE
    SYNTAX TruthValue
    MAX-ACCESS read-write
    STATUS current
    DESCRIPTION
        "This attribute specifies the threshold that must be exceeded to
        send the hpnicfPosaTcpConnectionExceed trap."
    DEFVAL { true }
    ::= { hpnicfPosaControl 14 }

hpnicfPosaFcmConnectionTrapEnable OBJECT-TYPE
    SYNTAX TruthValue
    MAX-ACCESS read-write
    STATUS current
    DESCRIPTION
        "This attribute specifies the threshold that must be exceeded to
        send the hpnicfPosaFcmConnectionExceed trap."
    DEFVAL { true }
    ::= { hpnicfPosaControl 15 }

hpnicfPosaTcpTradeLimit OBJECT-TYPE
    SYNTAX Integer32
    MAX-ACCESS read-write
    STATUS current
    DESCRIPTION
        "The limit of concurrent trades in one TCP connection.  The value 0
        means unlimited."
    DEFVAL {0}
    ::= { hpnicfPosaControl 16 }

hpnicfPosaTcpTradeTrapEnable OBJECT-TYPE
    SYNTAX TruthValue
    MAX-ACCESS read-write
    STATUS current
    DESCRIPTION
        "This attribute specifies the limit that must be exceeded to
        send the hpnicfPosaTcpTradeExceed trap."
    DEFVAL { true }
    ::= { hpnicfPosaControl 17 }

hpnicfPosaTcpTradeTimeout OBJECT-TYPE
    SYNTAX Integer32
    MAX-ACCESS read-write
    STATUS current
    DESCRIPTION
        "The maximum interval to wait for the reply from sending the trade
        packet to the application server.  The value 0 means wait forever."
    DEFVAL {240}
    ::= { hpnicfPosaControl 18 }

hpnicfPosaTradeSuccessFallingTrapEnable OBJECT-TYPE
    SYNTAX TruthValue
    MAX-ACCESS read-write
    STATUS current
    DESCRIPTION
        "This attribute controls whether the hpnicfPosaTradeSuccessFalling trap will
        be sent or not."
    DEFVAL { true }
    ::= { hpnicfPosaControl 19 }

hpnicfPosaTradeSuccessFallingThreshold OBJECT-TYPE
    SYNTAX Integer32
    MAX-ACCESS read-write
    STATUS current
    DESCRIPTION
        "The threshold of transaction success rate ."
    DEFVAL {90}
    ::= { hpnicfPosaControl 20 }

hpnicfPosaE1DialFallingTrapEnable OBJECT-TYPE
    SYNTAX TruthValue
    MAX-ACCESS read-write
    STATUS current
    DESCRIPTION
        "This attribute controls whether the hpnicfPosaE1DialFalling trap will
        be sent or not."
    DEFVAL { true }
    ::= { hpnicfPosaControl 21 }

hpnicfPosaE1DialFallingThreshold OBJECT-TYPE
    SYNTAX Integer32
    MAX-ACCESS read-write
    STATUS current
    DESCRIPTION
        "The threshold of dialing success rate ."
    DEFVAL {90}
    ::= { hpnicfPosaControl 22 }

hpnicfPosaFcmTradeAbnormalTrapEnable OBJECT-TYPE
    SYNTAX TruthValue
    MAX-ACCESS read-write
    STATUS current
    DESCRIPTION
        "This attribute controls whether the hpnicfPosaFcmTradeAbnormal trap will
        be sent or not."
    DEFVAL { true }
    ::= { hpnicfPosaControl 23 }

hpnicfPosaTables OBJECT IDENTIFIER ::= { hpnicfPosa 2 }

--
-- definition of hpnicfPosaAppTable
--

hpnicfPosaAppTable OBJECT-TYPE
    SYNTAX SEQUENCE OF HpnicfPosaAppEntry
    MAX-ACCESS not-accessible
    STATUS current
    DESCRIPTION
        "This table shows the configuration information and
        running status of POS application."
    ::= { hpnicfPosaTables 1 }

hpnicfPosaAppEntry OBJECT-TYPE
    SYNTAX HpnicfPosaAppEntry
    MAX-ACCESS not-accessible
    STATUS current
    DESCRIPTION
        "This table shows the configuration information and
        running status of POS application."
    INDEX { hpnicfPosaAppID }
    ::= { hpnicfPosaAppTable 1 }

HpnicfPosaAppEntry ::=
    SEQUENCE {
        hpnicfPosaAppID
            Integer32,
        hpnicfPosaAppServiceType
            HpnicfAppServiceType,
        hpnicfPosaAppIfIndex
            Integer32,
        hpnicfPosaAppMode
            HpnicfAppMode,
        hpnicfPosaAppHostIPType
            InetAddressType,
        hpnicfPosaAppHostIP
            InetAddress,
        hpnicfPosaAppHostPort
            Integer32,
        hpnicfPosaAppRouterIPType
            InetAddressType,
        hpnicfPosaAppRouterIP
            InetAddress,
        hpnicfPosaAppKeepAliveInterval
            Integer32,
        hpnicfPosaAppKeepAliveCount
            Integer32,
        hpnicfPosaAppConnectTimeout
            Integer32,
        hpnicfPosaAppState
            HpnicfPeerState,
        hpnicfPosaAppRowStatus
            RowStatus,
        hpnicfPosaAppName
            OCTET STRING,
        hpnicfPosaCallerIDTransEnable
            TruthValue,
        hpnicfPosaTpduChangeStrategy
            HpnicfTpduChangeStrategy,
        hpnicfPosaBackupAppID
            Integer32,
        hpnicfPosaQuietTimeOut
            Integer32,
        hpnicfPosaAppHello
            TruthValue,
        hpnicfPosaAppHelloInterval
            Integer32,
        hpnicfPosaAppRouterPort
            Integer32
     }

hpnicfPosaAppID OBJECT-TYPE
    SYNTAX Integer32 (1..1024)
    MAX-ACCESS accessible-for-notify
    STATUS current
    DESCRIPTION
        "The identification of a POS application."
    ::= { hpnicfPosaAppEntry 1 }

hpnicfPosaAppServiceType OBJECT-TYPE
    SYNTAX HpnicfAppServiceType
    MAX-ACCESS read-create
    STATUS current
    DESCRIPTION
        "The service type of a POS application.  It means the way
        in which the router connects with the application server."
    DEFVAL { tcp }
    ::= { hpnicfPosaAppEntry 2 }

hpnicfPosaAppIfIndex OBJECT-TYPE
    SYNTAX Integer32
    MAX-ACCESS read-create
    STATUS current
    DESCRIPTION
        "This attribute is the ifindex through which the router connecting with
        the application server, if the service type of POS application is flow(2).
        It is invalid if the service type is tcp(1).
        At preasent, it supports 5 types of interface: FCM, SERIAL, ASYNC,
        AM (Analog Modem) and AUX."
    REFERENCE
        "ifindex"
    ::= { hpnicfPosaAppEntry 3 }

hpnicfPosaAppMode OBJECT-TYPE
    SYNTAX HpnicfAppMode
    MAX-ACCESS read-create
    STATUS current
    DESCRIPTION
        "The work mode of a POS application."
    DEFVAL { normal }
    ::= { hpnicfPosaAppEntry 4 }

hpnicfPosaAppHostIPType OBJECT-TYPE
    SYNTAX InetAddressType
    MAX-ACCESS read-create
    STATUS current
    DESCRIPTION
        "The IP address type of the application server.  And now it must be IPV4.
        It is invalid if the service type is flow(2)."
    ::= { hpnicfPosaAppEntry 5 }

hpnicfPosaAppHostIP OBJECT-TYPE
    SYNTAX InetAddress
    MAX-ACCESS read-create
    STATUS current
    DESCRIPTION
        "The IP address of the application server.  And now it only supports IPV4.
        It is invalid if the service type is flow(2)."
    ::= { hpnicfPosaAppEntry 6 }

hpnicfPosaAppHostPort OBJECT-TYPE
    SYNTAX Integer32 (0..65535)
    MAX-ACCESS read-create
    STATUS current
    DESCRIPTION
        "The listening port of the application server.  If the information of
        the application server is not specified, this object will return the
        value 0.
        It is invalid if the service type is flow(2)."
    ::= { hpnicfPosaAppEntry 7 }

hpnicfPosaAppRouterIPType OBJECT-TYPE
    SYNTAX InetAddressType
    MAX-ACCESS read-create
    STATUS current
    DESCRIPTION
        "The source IP address type of the access router.  Now it must be ipv4.
        It is invalid if the service type is flow(2)."
    ::= { hpnicfPosaAppEntry 8 }

hpnicfPosaAppRouterIP OBJECT-TYPE
    SYNTAX InetAddress
    MAX-ACCESS read-create
    STATUS current
    DESCRIPTION
        "The source IP address of access router used in connecting with
        application server.  Now it only supports ipv4.
        It is invalid if the service type is flow(2)."
    ::= { hpnicfPosaAppEntry 9 }

hpnicfPosaAppKeepAliveInterval OBJECT-TYPE
    SYNTAX Integer32 (1..7200)
    UNITS "seconds"
    MAX-ACCESS read-create
    STATUS current
    DESCRIPTION
        "The TCP keep alive interval of the connection between the router and
        the application server.  In unit of seconds.
        The default value is 2 seconds.
        It is valid only when the service type is tcp(1)."
    DEFVAL { 2 }
    ::= { hpnicfPosaAppEntry 10 }

hpnicfPosaAppKeepAliveCount OBJECT-TYPE
    SYNTAX Integer32 (2..100)
    MAX-ACCESS read-create
    STATUS current
    DESCRIPTION
        "The maximum number of sending TCP keep alive packets.
        It is valid only when the service type is tcp(1)."
    DEFVAL { 3 }
    ::= { hpnicfPosaAppEntry 11 }

hpnicfPosaAppConnectTimeout OBJECT-TYPE
    SYNTAX Integer32 (1..20)
    UNITS "seconds"
    MAX-ACCESS read-create
    STATUS current
    DESCRIPTION
        "The maximum interval that the router waits for the reply from
        application server after sending the request for establishing a TCP
        connection.  It is invalid if the service type is flow(2)."
    DEFVAL { 20 }
    ::= { hpnicfPosaAppEntry 12 }

hpnicfPosaAppState OBJECT-TYPE
    SYNTAX HpnicfPeerState
    MAX-ACCESS read-only
    STATUS current
    DESCRIPTION
        "The current running state of application server."
    ::= { hpnicfPosaAppEntry 13 }

hpnicfPosaAppRowStatus OBJECT-TYPE
    SYNTAX RowStatus
    MAX-ACCESS read-create
    STATUS current
    DESCRIPTION
        "Operation status."
    ::= { hpnicfPosaAppEntry 14 }

hpnicfPosaAppName OBJECT-TYPE
    SYNTAX OCTET STRING (SIZE (0..32))
    MAX-ACCESS read-create
    STATUS current
    DESCRIPTION
        "The description of a POS application."
    ::= { hpnicfPosaAppEntry 15 }

hpnicfPosaCallerIDTransEnable OBJECT-TYPE
    SYNTAX TruthValue
    MAX-ACCESS read-create
    STATUS current
    DESCRIPTION
        "Enable or disable the caller-id transmission function."
    DEFVAL { false }
    ::= { hpnicfPosaAppEntry 16 }

hpnicfPosaTpduChangeStrategy OBJECT-TYPE
    SYNTAX HpnicfTpduChangeStrategy
    MAX-ACCESS read-create
    STATUS current
    DESCRIPTION
        "Set the strategy to modify the address of the packet from terminals
        before delivering it to application server."
    DEFVAL { changeTpduSrc }
    ::= { hpnicfPosaAppEntry 17 }

hpnicfPosaBackupAppID OBJECT-TYPE
    SYNTAX Integer32 (0..1024)
    MAX-ACCESS read-create
    STATUS current
    DESCRIPTION
        "Specify the backup application ID, 0 indicates not using backup application.
        It is invalid if the service type is flow(2)."
    ::= { hpnicfPosaAppEntry 18 }

hpnicfPosaQuietTimeOut OBJECT-TYPE
    SYNTAX Integer32 (10..600)
    MAX-ACCESS read-create
    STATUS current
    DESCRIPTION
        "Specify the wait time for re-activating application server.
        It is invalid if the service type is flow(2)."
    ::= { hpnicfPosaAppEntry 19 }

hpnicfPosaAppHello OBJECT-TYPE
    SYNTAX TruthValue
    MAX-ACCESS read-create
    STATUS current
    DESCRIPTION
        "Specify the switch of hello packet for the application server."
    DEFVAL { false }
    ::= { hpnicfPosaAppEntry 20 }

hpnicfPosaAppHelloInterval OBJECT-TYPE
    SYNTAX Integer32 (1..600)
    MAX-ACCESS read-create
    STATUS current
    DESCRIPTION
        "Specify the interval time in minute(s) of hello packet."
    DEFVAL { 1 }
    ::= { hpnicfPosaAppEntry 21 }

hpnicfPosaAppRouterPort OBJECT-TYPE
    SYNTAX Integer32 (0..4999)
    MAX-ACCESS read-create
    STATUS current
    DESCRIPTION
        "The source port of access router used in connecting with
        application server.  0 indicates not to specify the source port.
        It is valid only if the service type is tcp(1) and mode is normal(1)."
    ::= { hpnicfPosaAppEntry 22 }

--
-- definition of hpnicfPosaTerminalTable
--

hpnicfPosaTerminalTable OBJECT-TYPE
    SYNTAX SEQUENCE OF HpnicfPosaTerminalEntry
    MAX-ACCESS not-accessible
    STATUS current
    DESCRIPTION
        "This table shows the configuration information and
        running status of POS terminal."
    ::= { hpnicfPosaTables 2 }

hpnicfPosaTerminalEntry OBJECT-TYPE
    SYNTAX HpnicfPosaTerminalEntry
    MAX-ACCESS not-accessible
    STATUS current
    DESCRIPTION
        "This table shows the configuration information and
        running status of POS terminal."
    INDEX { hpnicfPosaTerminalID }
    ::= { hpnicfPosaTerminalTable 1 }

HpnicfPosaTerminalEntry ::=
    SEQUENCE {
        hpnicfPosaTerminalID
            Integer32,
        hpnicfPosaTerminalAccessType
            HpnicfTerminalAccessType,
        hpnicfPosaTerminalIfIndex
            Integer32,
        hpnicfPosaTerminalTransAppID
            Integer32,
        hpnicfPosaTerminalListenPort
            Integer32,
        hpnicfPosaTerminalState
            HpnicfPeerState,
        hpnicfPosaTerminalRowStatus
            RowStatus,
        hpnicfPosaTerminalName
            OCTET STRING,
        hpnicfPosaTerminalCfgIfIndex
            Integer32
     }

hpnicfPosaTerminalID OBJECT-TYPE
    SYNTAX Integer32 (1..1024)
    MAX-ACCESS accessible-for-notify
    STATUS current
    DESCRIPTION
        "The identification of a POS terminal."
    ::= { hpnicfPosaTerminalEntry 1 }

hpnicfPosaTerminalAccessType OBJECT-TYPE
    SYNTAX HpnicfTerminalAccessType
    MAX-ACCESS read-create
    STATUS current
    DESCRIPTION
        "The access type of a POS terminal."
    DEFVAL { fcm }
    ::= { hpnicfPosaTerminalEntry 2 }

hpnicfPosaTerminalIfIndex OBJECT-TYPE
    SYNTAX Integer32
    MAX-ACCESS read-create
    STATUS current
    DESCRIPTION
        "The ifindex of the interface through which connects the POS terminal
        and the router.  It is invalid if the access type is TCP."
    REFERENCE
        "ifindex"
    ::= { hpnicfPosaTerminalEntry 3 }

hpnicfPosaTerminalTransAppID OBJECT-TYPE
    SYNTAX Integer32 (0..1024)
    MAX-ACCESS read-create
    STATUS current
    DESCRIPTION
        "The identification of the application server to which all the packets
        from this POS terminal will be sent.
        If this object is set to 0, the destination application server to which
        a packet from this POS terminal will be sent is determined by its TPDU
        (Transport Protocol Data Unit) destination address.
        It is invalid if the access type is TCP."
    DEFVAL { 0 }
    ::= { hpnicfPosaTerminalEntry 4 }

hpnicfPosaTerminalListenPort OBJECT-TYPE
    SYNTAX Integer32 (0..65535)
    MAX-ACCESS read-create
    STATUS current
    DESCRIPTION
        "The listening port accepting the connection from POS terminals.
        It is valid only when the access type is TCP."
    ::= { hpnicfPosaTerminalEntry 5 }

hpnicfPosaTerminalState OBJECT-TYPE
    SYNTAX HpnicfPeerState
    MAX-ACCESS read-only
    STATUS current
    DESCRIPTION
        "The current running status of a POS terminal."
    ::= { hpnicfPosaTerminalEntry 6 }

hpnicfPosaTerminalRowStatus OBJECT-TYPE
    SYNTAX RowStatus
    MAX-ACCESS read-create
    STATUS current
    DESCRIPTION
        "Operation status."
    ::= { hpnicfPosaTerminalEntry 7 }

hpnicfPosaTerminalName OBJECT-TYPE
    SYNTAX OCTET STRING (SIZE (0..32))
    MAX-ACCESS read-create
    STATUS current
    DESCRIPTION
        "The description of a POS terminal."
    ::= { hpnicfPosaTerminalEntry 8 }

hpnicfPosaTerminalCfgIfIndex OBJECT-TYPE
    SYNTAX Integer32
    MAX-ACCESS read-only
    STATUS current
    DESCRIPTION
        "The ifindex of the interface on which the terminal configuration is.
        If it is a physical interface, its value is equal to that of
        hpnicfPosaTerminalIfIndex."
    REFERENCE
        "ifindex"
    ::= { hpnicfPosaTerminalEntry 9 }

--
-- definition of hpnicfPosaMapTable
--

hpnicfPosaMapTable OBJECT-TYPE
    SYNTAX SEQUENCE OF HpnicfPosaMapEntry
    MAX-ACCESS not-accessible
    STATUS current
    DESCRIPTION
        "This table describe the application-mapping information."
    ::= { hpnicfPosaTables 3 }

hpnicfPosaMapEntry OBJECT-TYPE
    SYNTAX HpnicfPosaMapEntry
    MAX-ACCESS not-accessible
    STATUS current
    DESCRIPTION
        "This table describe the application-mapping information."
    INDEX { hpnicfPosaMapSrcCode, hpnicfPosaMapDestCode }
    ::= { hpnicfPosaMapTable 1 }

HpnicfPosaMapEntry ::=
    SEQUENCE {
        hpnicfPosaMapDestCode
            OCTET STRING,
        hpnicfPosaMapAppID
            Integer32,
        hpnicfPosaMapRowStatus
            RowStatus,
        hpnicfPosaMapSrcCode
            OCTET STRING
     }

hpnicfPosaMapDestCode OBJECT-TYPE
    SYNTAX OCTET STRING (SIZE (4..7))
    MAX-ACCESS not-accessible
    STATUS current
    DESCRIPTION
        "The destination code of the mapping item.  Generally, the destination
        code is a 4-character-string.  If the destination address in POS packet
        matches the code, the packet will be deliveried to the corresponding
        application server.  If any code can not be matched, the packet will be
        deliveried to the default server.  A special destination code, 'default',
        is for default mapping item."
    ::= { hpnicfPosaMapEntry 1 }

hpnicfPosaMapAppID OBJECT-TYPE
    SYNTAX Integer32 (1..1024)
    MAX-ACCESS read-create
    STATUS current
    DESCRIPTION
        "The identifier of POS application.  It is the index of hpnicfPosaAppTable."
    ::= { hpnicfPosaMapEntry 2 }

hpnicfPosaMapRowStatus OBJECT-TYPE
    SYNTAX RowStatus
    MAX-ACCESS read-create
    STATUS current
    DESCRIPTION
        "Operation status."
    ::= { hpnicfPosaMapEntry 3 }

hpnicfPosaMapSrcCode OBJECT-TYPE
    SYNTAX OCTET STRING (SIZE (4..7))
    MAX-ACCESS not-accessible
    STATUS current
    DESCRIPTION
        "The source code of the mapping item.  Generally, the source code is a
        4-character-string.  If the source address in POS packet matches the
        code, the packet will be deliveried to the corresponding application
        server.  If any code can not be matched, the packet will be deliveried
        to the default server.  A special source code, 'default', is for
        default mapping item."
    ::= { hpnicfPosaMapEntry 4 }

--
-- definition of hpnicfPosaFcmStatTable
--

hpnicfPosaFcmStatTable OBJECT-TYPE
    SYNTAX SEQUENCE OF HpnicfPosaFcmStatEntry
    MAX-ACCESS not-accessible
    STATUS current
    DESCRIPTION
        "This table shows the statistics information of FCM interface."
    ::= { hpnicfPosaTables 4 }

hpnicfPosaFcmStatEntry OBJECT-TYPE
    SYNTAX HpnicfPosaFcmStatEntry
    MAX-ACCESS not-accessible
    STATUS current
    DESCRIPTION
        "This table shows the statistics information of FCM interface."
    INDEX { hpnicfPosaFcmStatIfIndex }
    ::= { hpnicfPosaFcmStatTable 1 }

HpnicfPosaFcmStatEntry ::=
    SEQUENCE {
        hpnicfPosaFcmStatIfIndex
            Integer32,
        hpnicfPosaFcmStatTimeoutCnts
            Counter32,
        hpnicfPosaFcmStatConnectFailCnts
            Counter32,
        hpnicfPosaFcmStatTransCnts
            Gauge32,
        hpnicfPosaFcmStatTransSuccessCnts
            Gauge32,
        hpnicfPosaFcmStatTransCntsClear
            TruthValue
     }

hpnicfPosaFcmStatIfIndex OBJECT-TYPE
    SYNTAX Integer32 (0..2147483647)
    MAX-ACCESS not-accessible
    STATUS current
    DESCRIPTION
        "The index of FCM interface."
    ::= { hpnicfPosaFcmStatEntry 1 }

hpnicfPosaFcmStatTimeoutCnts OBJECT-TYPE
    SYNTAX Counter32
    MAX-ACCESS read-only
    STATUS current
    DESCRIPTION
        "The number of disconnections because of trade timeouts."
    ::= { hpnicfPosaFcmStatEntry 2 }

hpnicfPosaFcmStatConnectFailCnts OBJECT-TYPE
    SYNTAX Counter32
    MAX-ACCESS read-only
    STATUS current
    DESCRIPTION
        "The number of connection failures because of unsuccessful negotiations."
    ::= { hpnicfPosaFcmStatEntry 3 }
hpnicfPosaFcmStatTransCnts OBJECT-TYPE
    SYNTAX Gauge32
    MAX-ACCESS read-only
    STATUS current
    DESCRIPTION
        "The number of all transactions made through the interface."
    ::= { hpnicfPosaFcmStatEntry 4 }

hpnicfPosaFcmStatTransSuccessCnts OBJECT-TYPE
    SYNTAX Gauge32
    MAX-ACCESS read-only
    STATUS current
    DESCRIPTION
        "The number of successful transactions made through the interface."
    ::= { hpnicfPosaFcmStatEntry 5 }

hpnicfPosaFcmStatTransCntsClear OBJECT-TYPE
    SYNTAX TruthValue
    MAX-ACCESS read-write
    STATUS current
    DESCRIPTION
        "Clear the number of successful transactions and all transactions."
    DEFVAL { false }
    ::= { hpnicfPosaFcmStatEntry 6 }

--
-- definition of hpnicfPosaAppStatTable
--

hpnicfPosaAppStatTable OBJECT-TYPE
    SYNTAX SEQUENCE OF HpnicfPosaAppStatEntry
    MAX-ACCESS not-accessible
    STATUS current
    DESCRIPTION
        "This table shows the statistics information of application."
    ::= { hpnicfPosaTables 5 }

hpnicfPosaAppStatEntry OBJECT-TYPE
    SYNTAX HpnicfPosaAppStatEntry
    MAX-ACCESS not-accessible
    STATUS current
    DESCRIPTION
        "This table shows the statistics information of application."
    INDEX { hpnicfPosaAppID }
    ::= { hpnicfPosaAppStatTable 1 }

HpnicfPosaAppStatEntry ::=
    SEQUENCE {
        hpnicfPosaAppRecvPkts
            Counter32,
        hpnicfPosaAppSendPkts
            Counter32,
        hpnicfPosaAppErrPkts
            Counter32,
        hpnicfPosaAppDistributeErrCnts
            Counter32,
        hpnicfPosaAppInDiscardedPkts
            Counter32,
        hpnicfPosaAppOutDiscardedPkts
            Counter32
     }

hpnicfPosaAppRecvPkts OBJECT-TYPE
    SYNTAX Counter32
    MAX-ACCESS read-only
    STATUS current
    DESCRIPTION
        "The number of packets recieved from the application server."
    ::= { hpnicfPosaAppStatEntry 1 }

hpnicfPosaAppSendPkts OBJECT-TYPE
    SYNTAX Counter32
    MAX-ACCESS read-only
    STATUS current
    DESCRIPTION
        "The number of packets sent to the application server."
    ::= { hpnicfPosaAppStatEntry 2 }

hpnicfPosaAppErrPkts OBJECT-TYPE
    SYNTAX Counter32
    MAX-ACCESS read-only
    STATUS current
    DESCRIPTION
        "The number of inbound packets that contained errors."
    ::= { hpnicfPosaAppStatEntry 3 }

hpnicfPosaAppDistributeErrCnts OBJECT-TYPE
    SYNTAX Counter32
    MAX-ACCESS read-only
    STATUS current
    DESCRIPTION
        "The number of packets that are discarded when no corresponding POS
        terminal can be found."
    ::= { hpnicfPosaAppStatEntry 4 }

hpnicfPosaAppInDiscardedPkts OBJECT-TYPE
    SYNTAX Counter32
    MAX-ACCESS read-only
    STATUS current
    DESCRIPTION
        "The number of inbound packets that are discarded when the incoming
        buffer is full."
    ::= { hpnicfPosaAppStatEntry 5 }

hpnicfPosaAppOutDiscardedPkts OBJECT-TYPE
    SYNTAX Counter32
    MAX-ACCESS read-only
    STATUS current
    DESCRIPTION
        "The number of outbound packets that are discarded because of link
        errors between the router and the application server."
    ::= { hpnicfPosaAppStatEntry 6 }

--
-- definition of hpnicfPosaTerminalStatTable
--

hpnicfPosaTerminalStatTable OBJECT-TYPE
    SYNTAX SEQUENCE OF HpnicfPosaTerminalStatEntry
    MAX-ACCESS not-accessible
    STATUS current
    DESCRIPTION
        "This table shows the statistics information of application."
    ::= { hpnicfPosaTables 6 }

hpnicfPosaTerminalStatEntry OBJECT-TYPE
    SYNTAX HpnicfPosaTerminalStatEntry
    MAX-ACCESS not-accessible
    STATUS current
    DESCRIPTION
        "This table shows the statistics information of application."
    INDEX { hpnicfPosaTerminalID }
    ::= { hpnicfPosaTerminalStatTable 1 }

HpnicfPosaTerminalStatEntry ::=
    SEQUENCE {
        hpnicfPosaTerminalRecvPkts
            Counter32,
        hpnicfPosaTerminalSendPkts
            Counter32,
        hpnicfPosaTerminalErrPkts
            Counter32,
        hpnicfPosaTerminalMapErrCnts
            Counter32,
        hpnicfPosaTerminalInDiscardedPkts
            Counter32,
        hpnicfPosaTerminalOutDiscardedPkts
            Counter32,
        hpnicfPosaTermianlTcpConnectionNumber
            Integer32
     }

hpnicfPosaTerminalRecvPkts OBJECT-TYPE
    SYNTAX Counter32
    MAX-ACCESS read-only
    STATUS current
    DESCRIPTION
        "The number of packets recieved from the POS terminal."
    ::= { hpnicfPosaTerminalStatEntry 1 }

hpnicfPosaTerminalSendPkts OBJECT-TYPE
    SYNTAX Counter32
    MAX-ACCESS read-only
    STATUS current
    DESCRIPTION
        "The number of packets sent to the POS terminal."
    ::= { hpnicfPosaTerminalStatEntry 2 }

hpnicfPosaTerminalErrPkts OBJECT-TYPE
    SYNTAX Counter32
    MAX-ACCESS read-only
    STATUS current
    DESCRIPTION
        "The number of inbound packets that contained errors."
    ::= { hpnicfPosaTerminalStatEntry 3 }

hpnicfPosaTerminalMapErrCnts OBJECT-TYPE
    SYNTAX Counter32
    MAX-ACCESS read-only
    STATUS current
    DESCRIPTION
        "The number of packets that are discarded because of mapping errors."
    ::= { hpnicfPosaTerminalStatEntry 4 }

hpnicfPosaTerminalInDiscardedPkts OBJECT-TYPE
    SYNTAX Counter32
    MAX-ACCESS read-only
    STATUS current
    DESCRIPTION
        "The number of inbound packets that are discarded when the incoming
        buffer is full."
    ::= { hpnicfPosaTerminalStatEntry 5 }

hpnicfPosaTerminalOutDiscardedPkts OBJECT-TYPE
    SYNTAX Counter32
    MAX-ACCESS read-only
    STATUS current
    DESCRIPTION
        "The number of outbound packets that are discarded because of link
        errors between the router and the POS terminal."
    ::= { hpnicfPosaTerminalStatEntry 6 }

hpnicfPosaTermianlTcpConnectionNumber OBJECT-TYPE
    SYNTAX Integer32
    MAX-ACCESS read-only
    STATUS current
    DESCRIPTION
        "The number of TCP connections between the router and the POS terminal."
    ::= { hpnicfPosaTerminalStatEntry 7 }

--
-- definition of hpnicfPosaBatchTerminalTable
--

hpnicfPosaBatchTerminalTable OBJECT-TYPE
    SYNTAX SEQUENCE OF HpnicfPosaBatchTerminalEntry
    MAX-ACCESS not-accessible
    STATUS current
    DESCRIPTION
        "The table of the configuration information relevant to
        a batch of POS terminals."
    ::= { hpnicfPosaTables 7 }

hpnicfPosaBatchTerminalEntry OBJECT-TYPE
    SYNTAX HpnicfPosaBatchTerminalEntry
    MAX-ACCESS not-accessible
    STATUS current
    DESCRIPTION
        "The configuration information relevant to a batch of
        POS terminals."
    INDEX { ifIndex }
    ::= { hpnicfPosaBatchTerminalTable 1 }

HpnicfPosaBatchTerminalEntry ::=
    SEQUENCE {
        hpnicfPosaBatchTerminalFirstID
            Integer32,
        hpnicfPosaBatchTerminalRowStatus
            RowStatus
     }

hpnicfPosaBatchTerminalFirstID OBJECT-TYPE
    SYNTAX Integer32 (1..1024)
    MAX-ACCESS read-create
    STATUS current
    DESCRIPTION
        "The first ID of the batch of POS terminals."
    ::= { hpnicfPosaBatchTerminalEntry 1 }

hpnicfPosaBatchTerminalRowStatus OBJECT-TYPE
    SYNTAX RowStatus
    MAX-ACCESS read-create
    STATUS current
    DESCRIPTION
        "Operation status."
    ::= { hpnicfPosaBatchTerminalEntry 2 }

--
-- definition of hpnicfPosaTcpTermStatTable
--

hpnicfPosaTcpTermStatTable OBJECT-TYPE
    SYNTAX SEQUENCE OF HpnicfPosaTcpTermStatEntry
    MAX-ACCESS not-accessible
    STATUS current
    DESCRIPTION
        "This table shows the statistics information of terminal whose
        access type is tcp."
    ::= { hpnicfPosaTables 8 }

hpnicfPosaTcpTermStatEntry OBJECT-TYPE
    SYNTAX HpnicfPosaTcpTermStatEntry
    MAX-ACCESS not-accessible
    STATUS current
    DESCRIPTION
        "This table shows the statistics information of terminal whose
        access type is tcp."
    INDEX { hpnicfPosaTcpTermStatIndex }
    ::= { hpnicfPosaTcpTermStatTable 1 }

HpnicfPosaTcpTermStatEntry ::=
    SEQUENCE {
        hpnicfPosaTcpTermStatIndex
            Integer32,
        hpnicfPosaTcpTermStatIPType
            InetAddressType,
        hpnicfPosaTcpTermStatIP
            InetAddress,
        hpnicfPosaTcpTermStatIPMask
            InetAddress,
        hpnicfPosaTcpTermRecvPkts
            Counter64,
        hpnicfPosaTcpTermSendPkts
            Counter64,
        hpnicfPosaTcpTermErrPkts
            Counter64,
        hpnicfPosaTcpTermMapErrCnts
            Counter64,
        hpnicfPosaTcpTermInDiscardedPkts
            Counter64,
        hpnicfPosaTcpTermOutDiscardedPkts
            Counter64,
        hpnicfPosaTcpTermStatRowStatus
            RowStatus
     }

hpnicfPosaTcpTermStatIndex OBJECT-TYPE
    SYNTAX Integer32 (1..64)
    MAX-ACCESS not-accessible
    STATUS current
    DESCRIPTION
        "The index of entity."
    ::= { hpnicfPosaTcpTermStatEntry 1 }

hpnicfPosaTcpTermStatIPType OBJECT-TYPE
    SYNTAX InetAddressType
    MAX-ACCESS read-create
    STATUS current
    DESCRIPTION
        "The type of Internet address.  And now it must be ipv4."
    ::= { hpnicfPosaTcpTermStatEntry 2 }

hpnicfPosaTcpTermStatIP OBJECT-TYPE
    SYNTAX InetAddress
    MAX-ACCESS read-create
    STATUS current
    DESCRIPTION
        "The IP address or the subnet of the statistics terminal(s).
        When the vlaue is a subnet, the statistics of all the
        terminals in the subnet will be added up.  And now it only
        supports ipv4."
    ::= { hpnicfPosaTcpTermStatEntry 3 }

hpnicfPosaTcpTermStatIPMask OBJECT-TYPE
    SYNTAX InetAddress
    MAX-ACCESS read-create
    STATUS current
    DESCRIPTION
        "The mask associated with the IP address or the subnet.  And
        now it only supports ipv4."
    ::= { hpnicfPosaTcpTermStatEntry 4 }

hpnicfPosaTcpTermRecvPkts OBJECT-TYPE
    SYNTAX Counter64
    MAX-ACCESS read-only
    STATUS current
    DESCRIPTION
        "The number of packets recieved from the POS terminal(s)."
    ::= { hpnicfPosaTcpTermStatEntry 5 }

hpnicfPosaTcpTermSendPkts OBJECT-TYPE
    SYNTAX Counter64
    MAX-ACCESS read-only
    STATUS current
    DESCRIPTION
        "The number of packets sent to the POS terminal(s)."
    ::= { hpnicfPosaTcpTermStatEntry 6 }

hpnicfPosaTcpTermErrPkts OBJECT-TYPE
    SYNTAX Counter64
    MAX-ACCESS read-only
    STATUS current
    DESCRIPTION
        "The number of inbound packets that contained errors."
    ::= { hpnicfPosaTcpTermStatEntry 7 }

hpnicfPosaTcpTermMapErrCnts OBJECT-TYPE
    SYNTAX Counter64
    MAX-ACCESS read-only
    STATUS current
    DESCRIPTION
        "The number of packets that are discarded because of mapping errors."
    ::= { hpnicfPosaTcpTermStatEntry 8 }

hpnicfPosaTcpTermInDiscardedPkts OBJECT-TYPE
    SYNTAX Counter64
    MAX-ACCESS read-only
    STATUS current
    DESCRIPTION
        "The number of inbound packets that are discarded when the incoming
        buffer is full."
    ::= { hpnicfPosaTcpTermStatEntry 9 }

hpnicfPosaTcpTermOutDiscardedPkts OBJECT-TYPE
    SYNTAX Counter64
    MAX-ACCESS read-only
    STATUS current
    DESCRIPTION
        "The number of outbound packets that are discarded because of link
        errors between the router and the POS terminal(s)."
    ::= { hpnicfPosaTcpTermStatEntry 10 }

hpnicfPosaTcpTermStatRowStatus OBJECT-TYPE
    SYNTAX RowStatus
    MAX-ACCESS read-create
    STATUS current
    DESCRIPTION
        "Operation status."
    ::= { hpnicfPosaTcpTermStatEntry 11 }

hpnicfPosaFcmConfTable OBJECT-TYPE
    SYNTAX      SEQUENCE OF HpnicfPosaFcmConfEntry
    MAX-ACCESS   not-accessible
    STATUS       current
    DESCRIPTION
        "This table shows the configuration information of FCM (Fast Connection
        Modem) interfaces."
    ::= { hpnicfPosaTables 9 }

hpnicfPosaFcmConfEntry OBJECT-TYPE
    SYNTAX         HpnicfPosaFcmConfEntry
    MAX-ACCESS     not-accessible
    STATUS         current
    DESCRIPTION
        "This entry shows the configuration information of FCM (Fast Connection
        Modem) interfaces."
    INDEX { ifIndex }
    ::= { hpnicfPosaFcmConfTable 1 }

HpnicfPosaFcmConfEntry ::= SEQUENCE  {
        hpnicfPosaFcmNegoHookOff         Integer32,
        hpnicfPosaFcmNegoSilence         Integer32,
        hpnicfPosaFcmNegoScrmbBinary1    Integer32,
        hpnicfPosaFcmNegoUnscrmbBinary1  Integer32,
        hpnicfPosaFcmThresholdRlsdOff    Integer32,
        hpnicfPosaFcmThresholdRlsdOn     Integer32,
        hpnicfPosaFcmThresholdTxPower    Integer32,
        hpnicfPosaFcmThresholdAnswerTone Integer32
        }

hpnicfPosaFcmNegoHookOff     OBJECT-TYPE
    SYNTAX   Integer32 (100..6000)
    UNITS       "milliseconds"
    MAX-ACCESS      read-write
    STATUS          current
    DESCRIPTION
        "Delay time for hookoff."
    DEFVAL { 500 }
    ::= { hpnicfPosaFcmConfEntry 1 }

hpnicfPosaFcmNegoSilence     OBJECT-TYPE
    SYNTAX   Integer32 (0..3000)
    UNITS       "milliseconds"
    MAX-ACCESS      read-write
    STATUS          current
    DESCRIPTION
        "Silence time for modem negotiation."
    DEFVAL { 0 }
    ::= { hpnicfPosaFcmConfEntry 2 }

hpnicfPosaFcmNegoScrmbBinary1 OBJECT-TYPE
    SYNTAX   Integer32 (100..1500)
    UNITS       "milliseconds"
    MAX-ACCESS      read-write
    STATUS          current
    DESCRIPTION
        "Scramble-binary1 time for modem negotiation."
    DEFVAL { 250 }
    ::= { hpnicfPosaFcmConfEntry 3 }

hpnicfPosaFcmNegoUnscrmbBinary1 OBJECT-TYPE
    SYNTAX   Integer32 (300..1500)
    UNITS       "milliseconds"
    MAX-ACCESS      read-write
    STATUS          current
    DESCRIPTION
        "Unscramble-binary1 time for modem negotiation."
    DEFVAL { 400 }
    ::= { hpnicfPosaFcmConfEntry 4 }

hpnicfPosaFcmThresholdRlsdOff  OBJECT-TYPE
    SYNTAX   Integer32 (0..75)
    UNITS       "-dBm"
    MAX-ACCESS      read-write
    STATUS          current
    DESCRIPTION
        "RLSD (Received Line Signal Detect) off threshold for modem."
    DEFVAL { 48 }
    ::= { hpnicfPosaFcmConfEntry 5 }

hpnicfPosaFcmThresholdRlsdOn  OBJECT-TYPE
    SYNTAX   Integer32 (0..75)
    UNITS       "-dBm"
    MAX-ACCESS      read-write
    STATUS          current
    DESCRIPTION
        "RLSD (Received Line Signal Detect) on threshold for modem."
    DEFVAL { 43 }
    ::= { hpnicfPosaFcmConfEntry 6 }

hpnicfPosaFcmThresholdTxPower OBJECT-TYPE
    SYNTAX   Integer32 (1..42)
    UNITS       "-dBm"
    MAX-ACCESS      read-write
    STATUS          current
    DESCRIPTION
        "TX power for modem."
    DEFVAL { 10 }
    ::= { hpnicfPosaFcmConfEntry 7 }

hpnicfPosaFcmThresholdAnswerTone OBJECT-TYPE
    SYNTAX   Integer32 (1..42)
    UNITS       "-dBm"
    MAX-ACCESS      read-write
    STATUS          current
    DESCRIPTION
        "Answer tone level for modem."
    DEFVAL { 9 }
    ::= { hpnicfPosaFcmConfEntry 8 }

hpnicfPosaCallerStatTable OBJECT-TYPE
    SYNTAX      SEQUENCE OF HpnicfPosaCallerStatEntry
    MAX-ACCESS   not-accessible
    STATUS       current
    DESCRIPTION
        "This table shows the statistics information of terminal according the
        caller-ID."
    ::= { hpnicfPosaTables 10 }

hpnicfPosaCallerStatEntry OBJECT-TYPE
    SYNTAX         HpnicfPosaCallerStatEntry
    MAX-ACCESS     not-accessible
    STATUS         current
    DESCRIPTION
        "This table shows the statistics information of terminal according the
        caller-ID."
    INDEX { hpnicfPosaCallerStatCallerID }
    ::= { hpnicfPosaCallerStatTable 1 }

HpnicfPosaCallerStatEntry ::= SEQUENCE  {
        hpnicfPosaCallerStatCallerID
            OCTET STRING,
        hpnicfPosaCallerRecvPkts
            Counter64,
        hpnicfPosaCallerSendPkts
            Counter64,
        hpnicfPosaCallerErrPkts
            Counter64,
        hpnicfPosaCallerMapErrCnts
            Counter64,
        hpnicfPosaCallerInDiscardedPkts
            Counter64,
        hpnicfPosaCallerOutDiscardedPkts
            Counter64,
        hpnicfPosaCallerStatRowStatus
            RowStatus
        }

hpnicfPosaCallerStatCallerID OBJECT-TYPE
    SYNTAX OCTET STRING (SIZE (0..64))
    MAX-ACCESS accessible-for-notify
    STATUS current
    DESCRIPTION
        "The caller number."
    ::= { hpnicfPosaCallerStatEntry 1 }

hpnicfPosaCallerRecvPkts OBJECT-TYPE
    SYNTAX Counter64
    MAX-ACCESS read-only
    STATUS current
    DESCRIPTION
        "The number of packets recieved from the POS terminal(s)."
    ::= { hpnicfPosaCallerStatEntry 2 }

hpnicfPosaCallerSendPkts OBJECT-TYPE
    SYNTAX Counter64
    MAX-ACCESS read-only
    STATUS current
    DESCRIPTION
        "The number of packets sent to the POS terminal(s)."
    ::= { hpnicfPosaCallerStatEntry 3 }

hpnicfPosaCallerErrPkts OBJECT-TYPE
    SYNTAX Counter64
    MAX-ACCESS read-only
    STATUS current
    DESCRIPTION
        "The number of inbound packets that contained errors."
    ::= { hpnicfPosaCallerStatEntry 4 }

hpnicfPosaCallerMapErrCnts OBJECT-TYPE
    SYNTAX Counter64
    MAX-ACCESS read-only
    STATUS current
    DESCRIPTION
        "The number of packets that are discarded because of mapping errors."
    ::= { hpnicfPosaCallerStatEntry 5 }

hpnicfPosaCallerInDiscardedPkts OBJECT-TYPE
    SYNTAX Counter64
    MAX-ACCESS read-only
    STATUS current
    DESCRIPTION
        "The number of inbound packets that are discarded when the incoming
        buffer is full."
    ::= { hpnicfPosaCallerStatEntry 6 }

hpnicfPosaCallerOutDiscardedPkts OBJECT-TYPE
    SYNTAX Counter64
    MAX-ACCESS read-only
    STATUS current
    DESCRIPTION
        "The number of outbound packets that are discarded because of link
        errors between the router and the POS terminal(s)."
    ::= { hpnicfPosaCallerStatEntry 7 }

hpnicfPosaCallerStatRowStatus OBJECT-TYPE
    SYNTAX RowStatus
    MAX-ACCESS read-create
    STATUS current
    DESCRIPTION
        "Operation status."
    ::= { hpnicfPosaCallerStatEntry 8 }

--
-- definition of hpnicfPosaNiiStatTable
--

hpnicfPosaNiiStatTable OBJECT-TYPE
    SYNTAX SEQUENCE OF HpnicfPosaNiiStatEntry
    MAX-ACCESS not-accessible
    STATUS current
    DESCRIPTION
        "This table shows statistics on the Network International Identifier."
    ::= { hpnicfPosaTables 11 }

hpnicfPosaNiiStatEntry OBJECT-TYPE
    SYNTAX HpnicfPosaNiiStatEntry
    MAX-ACCESS not-accessible
    STATUS current
    DESCRIPTION
        "This table shows statistics on the Network International Identifier."
    INDEX { hpnicfPosaNiiStatIndex }
    ::= { hpnicfPosaNiiStatTable 1 }

HpnicfPosaNiiStatEntry ::=
    SEQUENCE {
        hpnicfPosaNiiStatIndex
            OCTET STRING,
        hpnicfPosaNiiRecvPkts
            Counter32,
        hpnicfPosaNiiSendPkts
            Counter32,
        hpnicfPosaNiiSuccessTradeCnt
            Counter32,
        hpnicfPosaNiiTradeCnt
            Counter32
     }

hpnicfPosaNiiStatIndex OBJECT-TYPE
    SYNTAX OCTET STRING (SIZE (4))
    MAX-ACCESS accessible-for-notify
    STATUS current
    DESCRIPTION
        "The index of entity."
    ::= { hpnicfPosaNiiStatEntry 1 }

hpnicfPosaNiiRecvPkts OBJECT-TYPE
    SYNTAX Counter32
    MAX-ACCESS read-only
    STATUS current
    DESCRIPTION
        "The number of packets received from the POS terminals."
    ::= { hpnicfPosaNiiStatEntry 2 }

hpnicfPosaNiiSendPkts OBJECT-TYPE
    SYNTAX Counter32
    MAX-ACCESS read-only
    STATUS current
    DESCRIPTION
        "The number of packets sent to the POS terminals."
    ::= { hpnicfPosaNiiStatEntry 3 }

hpnicfPosaNiiSuccessTradeCnt OBJECT-TYPE
    SYNTAX Counter32
    MAX-ACCESS read-only
    STATUS current
    DESCRIPTION
        "The number of successful transactions of the Network International Identifier."
    ::= { hpnicfPosaNiiStatEntry 4 }

hpnicfPosaNiiTradeCnt OBJECT-TYPE
    SYNTAX Counter32
    MAX-ACCESS read-only
    STATUS current
    DESCRIPTION
        "The number of all transactions of the Network International Identifier."
    ::= { hpnicfPosaNiiStatEntry 5 }

--
-- definition of hpnicfPosaE1StatTable
--

hpnicfPosaE1StatTable OBJECT-TYPE
    SYNTAX SEQUENCE OF HpnicfPosaE1StatEntry
    MAX-ACCESS not-accessible
    STATUS current
    DESCRIPTION
        "This table shows statistics on E1-controller."
    ::= { hpnicfPosaTables 12 }

hpnicfPosaE1StatEntry OBJECT-TYPE
    SYNTAX HpnicfPosaE1StatEntry
    MAX-ACCESS not-accessible
    STATUS current
    DESCRIPTION
        "This table shows statistics on E1-controller."
    INDEX { hpnicfPosaE1StatIndex }
    ::= { hpnicfPosaE1StatTable 1 }

HpnicfPosaE1StatEntry ::=
    SEQUENCE {
        hpnicfPosaE1StatIndex
            Integer32,
        hpnicfPosaE1DialCnt
            Counter32,
        hpnicfPosaE1DialSuccess
            Counter32,
        hpnicfPosaE1RecvPkts
            Counter32,
        hpnicfPosaE1SendPkts
            Counter32,
        hpnicfPosaE1ErrPkts
            Counter32,
        hpnicfPosaE1MapErrCnts
            Counter32,
        hpnicfPosaE1InDiscardedPkts
            Counter32,
        hpnicfPosaE1OutDiscardedPkts
            Counter32
     }

hpnicfPosaE1StatIndex OBJECT-TYPE
    SYNTAX Integer32 (1..2147483647)
    MAX-ACCESS not-accessible
    STATUS current
    DESCRIPTION
        "The index of entity."
    ::= { hpnicfPosaE1StatEntry 1 }

hpnicfPosaE1DialCnt OBJECT-TYPE
    SYNTAX Counter32
    MAX-ACCESS read-only
    STATUS current
    DESCRIPTION
        "The number of dialing  from the E1-controller."
    ::= { hpnicfPosaE1StatEntry 2 }

hpnicfPosaE1DialSuccess OBJECT-TYPE
    SYNTAX Counter32
    MAX-ACCESS read-only
    STATUS current
    DESCRIPTION
        "The number of successful dialing  from the E1-controller."
    ::= { hpnicfPosaE1StatEntry 3 }

hpnicfPosaE1RecvPkts OBJECT-TYPE
    SYNTAX Counter32
    MAX-ACCESS read-only
    STATUS current
    DESCRIPTION
        "The number of packets received from the POS terminals."
    ::= { hpnicfPosaE1StatEntry 4 }

hpnicfPosaE1SendPkts OBJECT-TYPE
    SYNTAX Counter32
    MAX-ACCESS read-only
    STATUS current
    DESCRIPTION
        "The number of packets sent to the POS terminals."
    ::= { hpnicfPosaE1StatEntry 5 }

hpnicfPosaE1ErrPkts OBJECT-TYPE
    SYNTAX Counter32
    MAX-ACCESS read-only
    STATUS current
    DESCRIPTION
        "The number of inbound packets that contained errors."
    ::= { hpnicfPosaE1StatEntry 6 }

hpnicfPosaE1MapErrCnts OBJECT-TYPE
    SYNTAX Counter32
    MAX-ACCESS read-only
    STATUS current
    DESCRIPTION
        "The number of packets that are discarded because of mapping errors."
    ::= { hpnicfPosaE1StatEntry 7 }

hpnicfPosaE1InDiscardedPkts OBJECT-TYPE
    SYNTAX Counter32
    MAX-ACCESS read-only
    STATUS current
    DESCRIPTION
        "The number of inbound packets that are discarded when the incoming
        buffer is full."
    ::= { hpnicfPosaE1StatEntry 8 }

hpnicfPosaE1OutDiscardedPkts OBJECT-TYPE
    SYNTAX Counter32
    MAX-ACCESS read-only
    STATUS current
    DESCRIPTION
        "The number of outbound packets that are discarded because of link
        errors between the router and the POS terminal."
    ::= { hpnicfPosaE1StatEntry 9 }

--
-- traps defined
--

hpnicfPosaTrap OBJECT IDENTIFIER ::= { hpnicfPosa 3 }

hpnicfPosaTrapPrex OBJECT IDENTIFIER ::= { hpnicfPosaTrap 0 }

hpnicfPosaServerStatusChange NOTIFICATION-TYPE
    OBJECTS { hpnicfPosaServerEnable }
    STATUS current
    DESCRIPTION
        "This trap is generated when the POS function is started or stopped."
    ::= { hpnicfPosaTrapPrex 1 }

hpnicfPosaAppStateChange NOTIFICATION-TYPE
    OBJECTS { hpnicfPosaAppID, hpnicfPosaAppStateChangeObject }
    STATUS current
    DESCRIPTION
        "This trap is generated whenever the availability of application server
        changes."
    ::= { hpnicfPosaTrapPrex 2 }

hpnicfPosaTerminalHangUp NOTIFICATION-TYPE
    OBJECTS { ifIndex, ifDescr, hpnicfPosaCallerStatCallerID }
    STATUS current
    DESCRIPTION
        "This trap is generated whenever the POS connection through a FCM (Fast
        Connection Modem) interface is hanged up by POS terminal."
    ::= { hpnicfPosaTrapPrex 3 }

hpnicfPosaFcmLinkNegoFailed NOTIFICATION-TYPE
    OBJECTS { ifIndex, ifDescr , hpnicfPosaCallerStatCallerID }
    STATUS current
    DESCRIPTION
        "This trap is generated whenever the link layer negotiation is failed
        between the POS terminal and router through a FCM (Fast Connection
        Modem) interface."
    ::= { hpnicfPosaTrapPrex 4 }

hpnicfPosaFcmPhyNegoFailed NOTIFICATION-TYPE
    OBJECTS { ifIndex, ifDescr , hpnicfPosaCallerStatCallerID }
    STATUS current
    DESCRIPTION
        "This trap is generated whenever the physical layer negotiation is failed
        between the POS terminal and router through a FCM (Fast Connection
        Modem) interface."
    ::= { hpnicfPosaTrapPrex 5 }

hpnicfPosaTcpConnectionExceed NOTIFICATION-TYPE
    OBJECTS { hpnicfPosaTcpConnectionThreshold }
    STATUS current
    DESCRIPTION
        "This trap is generated whenever the number of connections exceeds the threshold."
    ::= { hpnicfPosaTrapPrex 6 }

hpnicfPosaFcmConnectionExceed NOTIFICATION-TYPE
    OBJECTS { hpnicfPosaFcmConnectionThreshold }
    STATUS current
    DESCRIPTION
        "This trap is generated whenever the number of connections exceeds the threshold."
    ::= { hpnicfPosaTrapPrex 7 }

hpnicfPosaTcpTradeExceed NOTIFICATION-TYPE
    OBJECTS { hpnicfPosaTcpTradeLimit, hpnicfPosaTerminalID }
    STATUS current
    DESCRIPTION
        "This trap is generated whenever the number of trades in any TCP connect exceeds
        the limit."
    ::= { hpnicfPosaTrapPrex 8 }

hpnicfPosaTradeSuccessFalling NOTIFICATION-TYPE
    OBJECTS { hpnicfPosaNiiStatIndex, hpnicfPosaTradeSuccessFallingThreshold }
    STATUS current
    DESCRIPTION
        "This trap is generated whenever the transaction success rate of bank server is smaller than or equal to the threshold."
    ::= { hpnicfPosaTrapPrex 9 }

hpnicfPosaE1DialFalling NOTIFICATION-TYPE
    OBJECTS { ifIndex, ifDescr, hpnicfPosaE1DialFallingThreshold }
    STATUS current
    DESCRIPTION
        "This trap is generated whenever the dialing success rate of E1-controller is smaller than or equal to the threshold."
    ::= { hpnicfPosaTrapPrex 10 }

hpnicfPosaFcmTradeAbnormal NOTIFICATION-TYPE
    OBJECTS { ifIndex, ifDescr, hpnicfPosaCallerStatCallerID }
    STATUS current
    DESCRIPTION
        "This trap is generated whenever the dialing link is abnormal."
    ::= { hpnicfPosaTrapPrex 11 }

hpnicfPosaTrapObjects OBJECT IDENTIFIER ::= { hpnicfPosaTrap 1 }

hpnicfPosaAppStateChangeObject OBJECT-TYPE
    SYNTAX INTEGER
        {
        available(1),
        unavailable(2)
        }
    MAX-ACCESS accessible-for-notify
    STATUS current
    DESCRIPTION
        "This is a dummy MIB object referenced by the hpnicfPosaAppStateChange trap.
        This object shows the availability changing of corresponding application
        server."
    ::= { hpnicfPosaTrapObjects 1 }

END
