-- ============================================================================
-- Copyright (c) 2010-2016 Hewlett-Packard Development Company, L.P.
-- Description: This MIB will maintain the products MIB OID and management
--              properties root node for HPN products
--
-- Reference:
-- Version: V1.07
-- History:
--   V1.00 2013/01/08 Created by songhao
--   V1.01 2013/04/26 add hpnicfEvb, hpnicfFcoeMode, hpnicfMDC, hpnicfQinQv2, hpnicfVmap
--                    modify name of 127, 129, 132 under hpnicfCommon by songhao
--   V1.02 2013/09/22 remove hpnicfFdmi under hpnicfCommon
--                    add hpnicfL2tp, hpnicfMultilinkPPPV2, hpnicfBpa by songhao
--   V1.03 2014/01/27 add hpnicfLocAAASrv, hpnicfMplsExt, hpnicfMplsTe, hpnicfLicense,
--                        hpnicfLBv2, hpnicfSession, hpnicfARPSourceSuppression, hpnicfVxlan
--                        under hpnicfCommon by songhao
--   V1.04 2014/04/27 add hpnicfRddc, hpnicfIpRanDcn, hpnicfContext
--                    modify name of 129 under hpnicfCommon by songhao
--   V1.05 2014/09/18 add hpnicfMulticastSnoop, hpnicfPvst, hpnicfSmlk,
--                        hpnicf8021XExt2, hpnicfObjp, hpnicfNvgre by songhao
--   V1.06 2015/04/23 add 157 to 162 under hpnicfCommon by songhao
--   V1.07 2016/04/02 add 163 to 165 under hpnicfCommon by songhao
-- ============================================================================
HPN-ICF-OID-MIB DEFINITIONS ::= BEGIN
    IMPORTS
        enterprises
            FROM RFC1155-SMI;

-- Objects under .enterprises
    hp                              OBJECT IDENTIFIER ::= { enterprises 11 }
    nm                              OBJECT IDENTIFIER ::= { hp 2 }
    icf                             OBJECT IDENTIFIER ::= { nm 14 }
    hpicfObjects                    OBJECT IDENTIFIER ::= { icf 11 }
    hpnicf                          OBJECT IDENTIFIER ::= { hpicfObjects 15 }

-- Objects under .enterprises.hp(11).nm(2).icf(14).hpicfObjects(11).hpnicf(15)
    -- hpnicfProductId                 OBJECT IDENTIFIER ::= { hpnicf 1 }
    hpnicfCommon                    OBJECT IDENTIFIER ::= { hpnicf 2 }
    hpnicfEntityVendorTypeOID       OBJECT IDENTIFIER ::= { hpnicf 3 }
    hpnicfNM                        OBJECT IDENTIFIER ::= { hpnicf 4 }
    hpnicfSystem                    OBJECT IDENTIFIER ::= { hpnicf 6 }
    hpnicfSNMPAgCpb                 OBJECT IDENTIFIER ::= { hpnicf 7 }
    hpnicfRhw                       OBJECT IDENTIFIER ::= { hpnicf 8 }
    -- hpnicfSurveillanceMIB           OBJECT IDENTIFIER ::= { hpnicf 9 }
    -- hpnicfStorageRef                OBJECT IDENTIFIER ::= { hpnicf 10 }

-- Object under .hpnicf.hpnicfCommon(2)
    hpnicfFtm                       OBJECT IDENTIFIER ::= { hpnicfCommon 1 }
    hpnicfUIMgt                     OBJECT IDENTIFIER ::= { hpnicfCommon 2 }
    hpnicfSystemMan                 OBJECT IDENTIFIER ::= { hpnicfCommon 3 }
    hpnicfConfig                    OBJECT IDENTIFIER ::= { hpnicfCommon 4 }
    hpnicfFlash                     OBJECT IDENTIFIER ::= { hpnicfCommon 5 }
    hpnicfEntityExtend              OBJECT IDENTIFIER ::= { hpnicfCommon 6 }
    hpnicfIPSecMonitor              OBJECT IDENTIFIER ::= { hpnicfCommon 7 }
    hpnicfAcl                       OBJECT IDENTIFIER ::= { hpnicfCommon 8 }
    hpnicfVoiceVlan                 OBJECT IDENTIFIER ::= { hpnicfCommon 9 }
    hpnicfL4Redirect                OBJECT IDENTIFIER ::= { hpnicfCommon 10 }
    hpnicfIpPBX                     OBJECT IDENTIFIER ::= { hpnicfCommon 11 }
    hpnicfUser                      OBJECT IDENTIFIER ::= { hpnicfCommon 12 }
    hpnicfRadius                    OBJECT IDENTIFIER ::= { hpnicfCommon 13 }
    hpnicfPowerEthernetExt          OBJECT IDENTIFIER ::= { hpnicfCommon 14 }
    hpnicfEntityRelation            OBJECT IDENTIFIER ::= { hpnicfCommon 15 }
    hpnicfProtocolVlan              OBJECT IDENTIFIER ::= { hpnicfCommon 16 }
    hpnicfQosProfile                OBJECT IDENTIFIER ::= { hpnicfCommon 17 }
    hpnicfNat                       OBJECT IDENTIFIER ::= { hpnicfCommon 18 }
    hpnicfPos                       OBJECT IDENTIFIER ::= { hpnicfCommon 19 }
    hpnicfNS                        OBJECT IDENTIFIER ::= { hpnicfCommon 20 }
    hpnicfAAL5                      OBJECT IDENTIFIER ::= { hpnicfCommon 21 }
    hpnicfSSH                       OBJECT IDENTIFIER ::= { hpnicfCommon 22 }
    hpnicfRSA                       OBJECT IDENTIFIER ::= { hpnicfCommon 23 }
    hpnicfVrrpExt                   OBJECT IDENTIFIER ::= { hpnicfCommon 24 }
    hpnicfIpa                       OBJECT IDENTIFIER ::= { hpnicfCommon 25 }
    hpnicfPortSecurity              OBJECT IDENTIFIER ::= { hpnicfCommon 26 }
    hpnicfVpls                      OBJECT IDENTIFIER ::= { hpnicfCommon 27 }
    hpnicfE1                        OBJECT IDENTIFIER ::= { hpnicfCommon 28 }
    hpnicfT1                        OBJECT IDENTIFIER ::= { hpnicfCommon 29 }
    hpnicfIKEMonitor                OBJECT IDENTIFIER ::= { hpnicfCommon 30 }
    hpnicfWebSwitch                 OBJECT IDENTIFIER ::= { hpnicfCommon 31 }
    hpnicfAutoDetect                OBJECT IDENTIFIER ::= { hpnicfCommon 32 }
    hpnicfIpBroadcast               OBJECT IDENTIFIER ::= { hpnicfCommon 33 }
    hpnicfIpx                       OBJECT IDENTIFIER ::= { hpnicfCommon 34 }
    hpnicfIPS                       OBJECT IDENTIFIER ::= { hpnicfCommon 35 }
    hpnicfDhcpSnoop                 OBJECT IDENTIFIER ::= { hpnicfCommon 36 }
    hpnicfProtocolPriority          OBJECT IDENTIFIER ::= { hpnicfCommon 37 }
    hpnicfTrap                      OBJECT IDENTIFIER ::= { hpnicfCommon 38 }
    hpnicfVoice                     OBJECT IDENTIFIER ::= { hpnicfCommon 39 }
    hpnicfIfExt                     OBJECT IDENTIFIER ::= { hpnicfCommon 40 }
    hpnicfCfCard                    OBJECT IDENTIFIER ::= { hpnicfCommon 41 }
    hpnicfEpon                      OBJECT IDENTIFIER ::= { hpnicfCommon 42 }
    hpnicfDldp                      OBJECT IDENTIFIER ::= { hpnicfCommon 43 }
    hpnicfUnicast                   OBJECT IDENTIFIER ::= { hpnicfCommon 44 }
    hpnicfRrpp                      OBJECT IDENTIFIER ::= { hpnicfCommon 45 }
    hpnicfDomain                    OBJECT IDENTIFIER ::= { hpnicfCommon 46 }
    hpnicfIds                       OBJECT IDENTIFIER ::= { hpnicfCommon 47 }
    hpnicfRcr                       OBJECT IDENTIFIER ::= { hpnicfCommon 48 }
    hpnicfAtmDxi                    OBJECT IDENTIFIER ::= { hpnicfCommon 49 }
    hpnicfMulticast                 OBJECT IDENTIFIER ::= { hpnicfCommon 50 }
    hpnicfMpm                       OBJECT IDENTIFIER ::= { hpnicfCommon 51 }
    hpnicfOadp                      OBJECT IDENTIFIER ::= { hpnicfCommon 52 }
    hpnicfTunnel                    OBJECT IDENTIFIER ::= { hpnicfCommon 53 }
    hpnicfGre                       OBJECT IDENTIFIER ::= { hpnicfCommon 54 }
    hpnicfObjectInfo                OBJECT IDENTIFIER ::= { hpnicfCommon 55 }
    hpnicfStorage                   OBJECT IDENTIFIER ::= { hpnicfCommon 56 }
    hpnicfDvpn                      OBJECT IDENTIFIER ::= { hpnicfCommon 57 }
    hpnicfDhcpRelay                 OBJECT IDENTIFIER ::= { hpnicfCommon 58 }
    hpnicfIsis                      OBJECT IDENTIFIER ::= { hpnicfCommon 59 }
    hpnicfRpr                       OBJECT IDENTIFIER ::= { hpnicfCommon 60 }
    hpnicfSubnetVlan                OBJECT IDENTIFIER ::= { hpnicfCommon 61 }
    hpnicfDlswExt                   OBJECT IDENTIFIER ::= { hpnicfCommon 62 }
    hpnicfSyslog                    OBJECT IDENTIFIER ::= { hpnicfCommon 63 }
    hpnicfFlowTemplate              OBJECT IDENTIFIER ::= { hpnicfCommon 64 }
    hpnicfQos2                      OBJECT IDENTIFIER ::= { hpnicfCommon 65 }
    hpnicfStormConstrain            OBJECT IDENTIFIER ::= { hpnicfCommon 66 }
    hpnicfIpAddrMIB                 OBJECT IDENTIFIER ::= { hpnicfCommon 67 }
    hpnicfMirrGroup                 OBJECT IDENTIFIER ::= { hpnicfCommon 68 }
    hpnicfQINQ                      OBJECT IDENTIFIER ::= { hpnicfCommon 69 }
    hpnicfTransceiver               OBJECT IDENTIFIER ::= { hpnicfCommon 70 }
    hpnicfIpv6AddrMIB               OBJECT IDENTIFIER ::= { hpnicfCommon 71 }
    hpnicfBfdMIB                    OBJECT IDENTIFIER ::= { hpnicfCommon 72 }
    hpnicfRCP                       OBJECT IDENTIFIER ::= { hpnicfCommon 73 }
    hpnicfAcfp                      OBJECT IDENTIFIER ::= { hpnicfCommon 74 }
    hpnicfDot11                     OBJECT IDENTIFIER ::= { hpnicfCommon 75 }
    hpnicfE1T1VI                    OBJECT IDENTIFIER ::= { hpnicfCommon 76 }
    hpnicfL2VpnPwe3                 OBJECT IDENTIFIER ::= { hpnicfCommon 78 }
    hpnicfMplsOam                   OBJECT IDENTIFIER ::= { hpnicfCommon 79 }
    hpnicfMplsOamPs                 OBJECT IDENTIFIER ::= { hpnicfCommon 80 }
    hpnicfSiemMib                   OBJECT IDENTIFIER ::= { hpnicfCommon 81 }
    hpnicfUps                       OBJECT IDENTIFIER ::= { hpnicfCommon 82 }
    hpnicfEOCCommon                 OBJECT IDENTIFIER ::= { hpnicfCommon 83 }
    hpnicfHPEOC                     OBJECT IDENTIFIER ::= { hpnicfCommon 84 }
    hpnicfAFC                       OBJECT IDENTIFIER ::= { hpnicfCommon 85 }
    hpnicfMultCDR                   OBJECT IDENTIFIER ::= { hpnicfCommon 86 }
    hpnicfMACInformation            OBJECT IDENTIFIER ::= { hpnicfCommon 87 }
    hpnicfFireWall                  OBJECT IDENTIFIER ::= { hpnicfCommon 88 }
    hpnicfDSP                       OBJECT IDENTIFIER ::= { hpnicfCommon 89 }
    hpnicfNetMan                    OBJECT IDENTIFIER ::= { hpnicfCommon 90 }
    hpnicfStack                     OBJECT IDENTIFIER ::= { hpnicfCommon 91 }
    hpnicfPosa                      OBJECT IDENTIFIER ::= { hpnicfCommon 92 }
    hpnicfWebAuthentication         OBJECT IDENTIFIER ::= { hpnicfCommon 93 }
    hpnicfCATVTransceiver           OBJECT IDENTIFIER ::= { hpnicfCommon 94 }
    hpnicfLpbkdt                    OBJECT IDENTIFIER ::= { hpnicfCommon 95 }
    hpnicfMultiMedia                OBJECT IDENTIFIER ::= { hpnicfCommon 96 }
    hpnicfDns                       OBJECT IDENTIFIER ::= { hpnicfCommon 97 }
    hpnicf3GModem                   OBJECT IDENTIFIER ::= { hpnicfCommon 98 }
    hpnicfPortal                    OBJECT IDENTIFIER ::= { hpnicfCommon 99 }
    hpnicflldp                      OBJECT IDENTIFIER ::= { hpnicfCommon 100 }
    hpnicfDHCPServer                OBJECT IDENTIFIER ::= { hpnicfCommon 101 }
    hpnicfPPPoEServer               OBJECT IDENTIFIER ::= { hpnicfCommon 102 }
    hpnicfL2Isolate                 OBJECT IDENTIFIER ::= { hpnicfCommon 103 }
    hpnicfSnmpExt                   OBJECT IDENTIFIER ::= { hpnicfCommon 104 }
    hpnicfVsi                       OBJECT IDENTIFIER ::= { hpnicfCommon 105 }
    hpnicfEvc                       OBJECT IDENTIFIER ::= { hpnicfCommon 106 }
    hpnicfMinm                      OBJECT IDENTIFIER ::= { hpnicfCommon 107 }
    hpnicfBlg                       OBJECT IDENTIFIER ::= { hpnicfCommon 108 }
    hpnicfRS485                     OBJECT IDENTIFIER ::= { hpnicfCommon 109 }
    hpnicfARPRatelimit              OBJECT IDENTIFIER ::= { hpnicfCommon 110 }
    hpnicfLI                        OBJECT IDENTIFIER ::= { hpnicfCommon 111 }
    hpnicfDar                       OBJECT IDENTIFIER ::= { hpnicfCommon 112 }
    hpnicfPBR                       OBJECT IDENTIFIER ::= { hpnicfCommon 113 }
    hpnicfAAANasId                  OBJECT IDENTIFIER ::= { hpnicfCommon 114 }
    hpnicfTeTunnel                  OBJECT IDENTIFIER ::= { hpnicfCommon 115 }
    hpnicfLB                        OBJECT IDENTIFIER ::= { hpnicfCommon 116 }
    hpnicfDldp2                     OBJECT IDENTIFIER ::= { hpnicfCommon 117 }
    hpnicfWIPS                      OBJECT IDENTIFIER ::= { hpnicfCommon 118 }
    hpnicfInfoCenter                OBJECT IDENTIFIER ::= { hpnicfCommon 119 }
    hpnicfFCoE                      OBJECT IDENTIFIER ::= { hpnicfCommon 120 }
    hpnicfTRNG2                     OBJECT IDENTIFIER ::= { hpnicfCommon 121 }
    hpnicfDhcp4                     OBJECT IDENTIFIER ::= { hpnicfCommon 122 }
    hpnicfMulticastSnoop            OBJECT IDENTIFIER ::= { hpnicfCommon 123 }
    hpnicfDhcpSnoop2                OBJECT IDENTIFIER ::= { hpnicfCommon 124 }
    hpnicfRmonExt                   OBJECT IDENTIFIER ::= { hpnicfCommon 125 }
    hpnicfIPsecMonitorV2            OBJECT IDENTIFIER ::= { hpnicfCommon 126 }
    hpnicfSan                       OBJECT IDENTIFIER ::= { hpnicfCommon 127 }
    hpnicfSpb                       OBJECT IDENTIFIER ::= { hpnicfCommon 128 }
    hpnicfPex                       OBJECT IDENTIFIER ::= { hpnicfCommon 129 }
    hpnicfSlbg                      OBJECT IDENTIFIER ::= { hpnicfCommon 130 }
    hpnicfPvst                      OBJECT IDENTIFIER ::= { hpnicfCommon 131 }
    hpnicfEvi                       OBJECT IDENTIFIER ::= { hpnicfCommon 132 }
    hpnicfIssuUpgrade               OBJECT IDENTIFIER ::= { hpnicfCommon 133 }
    hpnicfEvb                       OBJECT IDENTIFIER ::= { hpnicfCommon 134 }
    hpnicfFcoeMode                  OBJECT IDENTIFIER ::= { hpnicfCommon 135 }
    hpnicfMDC                       OBJECT IDENTIFIER ::= { hpnicfCommon 136 }
    hpnicfQinQv2                    OBJECT IDENTIFIER ::= { hpnicfCommon 137 }
    hpnicfVmap                      OBJECT IDENTIFIER ::= { hpnicfCommon 138 }
    hpnicfL2tp                      OBJECT IDENTIFIER ::= { hpnicfCommon 139 }
    hpnicfMultilinkPPPV2            OBJECT IDENTIFIER ::= { hpnicfCommon 140 }
    hpnicfLocAAASrv                 OBJECT IDENTIFIER ::= { hpnicfCommon 141 }
    hpnicfMplsExt                   OBJECT IDENTIFIER ::= { hpnicfCommon 142 }
    hpnicfMplsTe                    OBJECT IDENTIFIER ::= { hpnicfCommon 143 }
    hpnicfBpa                       OBJECT IDENTIFIER ::= { hpnicfCommon 144 }
    hpnicfLicense                   OBJECT IDENTIFIER ::= { hpnicfCommon 145 }
    hpnicfSmlk                      OBJECT IDENTIFIER ::= { hpnicfCommon 147 }
    hpnicfARPSourceSuppression      OBJECT IDENTIFIER ::= { hpnicfCommon 146 }
    hpnicfLBv2                      OBJECT IDENTIFIER ::= { hpnicfCommon 148 }
    hpnicfSession                   OBJECT IDENTIFIER ::= { hpnicfCommon 149 }
    hpnicfVxlan                     OBJECT IDENTIFIER ::= { hpnicfCommon 150 }
    hpnicfRddc                      OBJECT IDENTIFIER ::= { hpnicfCommon 151 }
    hpnicfIpRanDcn                  OBJECT IDENTIFIER ::= { hpnicfCommon 152 }
    hpnicf8021XExt2                 OBJECT IDENTIFIER ::= { hpnicfCommon 153 }
    hpnicfContext                   OBJECT IDENTIFIER ::= { hpnicfCommon 154 }
    hpnicfObjp                      OBJECT IDENTIFIER ::= { hpnicfCommon 155 }
    hpnicfNvgre                     OBJECT IDENTIFIER ::= { hpnicfCommon 156 }
    hpnicfWlanMt                    OBJECT IDENTIFIER ::= { hpnicfCommon 157 }
    hpnicfRbac                      OBJECT IDENTIFIER ::= { hpnicfCommon 158 }
    hpnicfDHCP6Server               OBJECT IDENTIFIER ::= { hpnicfCommon 159 }
    hpnicfMplsVpnBgp                OBJECT IDENTIFIER ::= { hpnicfCommon 160 }
    hpnicfOspf                      OBJECT IDENTIFIER ::= { hpnicfCommon 161 }
    hpnicfL2vpn                     OBJECT IDENTIFIER ::= { hpnicfCommon 162 }
    hpnicfMACsec                    OBJECT IDENTIFIER ::= { hpnicfCommon 163 }
    hpnicfFailover                  OBJECT IDENTIFIER ::= { hpnicfCommon 164 }
    hpnicfVpnPeer                   OBJECT IDENTIFIER ::= { hpnicfCommon 165 }

-- Objects under .hpnicf.hpnicfCommon(2).hpnicfQos2(65)
    hpnicfIfQos2                    OBJECT IDENTIFIER ::= { hpnicfQos2 1 }
    hpnicfCBQos2                    OBJECT IDENTIFIER ::= { hpnicfQos2 2 }

-- Objects under .hpnicf.hpnicfSNMPAgCpb(7)
    hpnicfQosCapability             OBJECT IDENTIFIER ::= { hpnicfSNMPAgCpb 1 }

-- Objects under .hpnicf.hpnicfRhw(8)
    hpnicfDHCPRelayMib              OBJECT IDENTIFIER ::= { hpnicfRhw 1 }
    hpnicfDHCPServerMib             OBJECT IDENTIFIER ::= { hpnicfRhw 2 }
    hpnicfNqa                       OBJECT IDENTIFIER ::= { hpnicfRhw 3 }
    hpnicfrmonExtend                OBJECT IDENTIFIER ::= { hpnicfRhw 4 }
    hpnicfpaeExtMib                 OBJECT IDENTIFIER ::= { hpnicfRhw 6 }
    hpnicfHgmp                      OBJECT IDENTIFIER ::= { hpnicfRhw 7 }
    hpnicfDevice                    OBJECT IDENTIFIER ::= { hpnicfRhw 8 }
    hpnicfMpls                      OBJECT IDENTIFIER ::= { hpnicfRhw 12 }
    hpnicfTRNG                      OBJECT IDENTIFIER ::= { hpnicfRhw 13 }
    hpnicfUserLogMIB                OBJECT IDENTIFIER ::= { hpnicfRhw 18 }
    hpnicfNTP                       OBJECT IDENTIFIER ::= { hpnicfRhw 22 }
    hpnicfLAG                       OBJECT IDENTIFIER ::= { hpnicfRhw 25 }
    hpnicfSmonExtend                OBJECT IDENTIFIER ::= { hpnicfRhw 26 }
    hpnicfQoS                       OBJECT IDENTIFIER ::= { hpnicfRhw 32 }
    hpnicfMultilinkPPP              OBJECT IDENTIFIER ::= { hpnicfRhw 33 }
    hpnicflswCommon                 OBJECT IDENTIFIER ::= { hpnicfRhw 35 }
    -- hpnicfmlsr                      OBJECT IDENTIFIER ::= { hpnicfRhw 36 }
    -- hpnicfdlsw                      OBJECT IDENTIFIER ::= { hpnicfRhw 37 }

-- Objects under .hpnicf.hpnicfRhw(8).hpnicfMpls(12)
    hpnicfMplsLsr                   OBJECT IDENTIFIER ::= { hpnicfMpls 1 }
    hpnicfMplsLdp                   OBJECT IDENTIFIER ::= { hpnicfMpls 2 }
    hpnicfMplsVpn                   OBJECT IDENTIFIER ::= { hpnicfMpls 3 }

-- Objects under .hpnicf.hpnicfRhw(8).hpnicflswCommon(35)
    hpnicfLswExtInterface           OBJECT IDENTIFIER ::= { hpnicflswCommon 1 }
    hpnicfLswVlan                   OBJECT IDENTIFIER ::= { hpnicflswCommon 2 }
    hpnicfLswMacPort                OBJECT IDENTIFIER ::= { hpnicflswCommon 3 }
    hpnicfLswArpMib                 OBJECT IDENTIFIER ::= { hpnicflswCommon 4 }
    hpnicfLswL2InfMib               OBJECT IDENTIFIER ::= { hpnicflswCommon 5 }
    hpnicfLswRstpMib                OBJECT IDENTIFIER ::= { hpnicflswCommon 6 }
    hpnicfLswIgmpsnoopingMib        OBJECT IDENTIFIER ::= { hpnicflswCommon 7 }
    hpnicfLswDhcpMib                OBJECT IDENTIFIER ::= { hpnicflswCommon 8 }
    hpnicfLswdevMMib                OBJECT IDENTIFIER ::= { hpnicflswCommon 9 }
    hpnicfLswTrapMib                OBJECT IDENTIFIER ::= { hpnicflswCommon 12 }
    hpnicfdot1sMstp                 OBJECT IDENTIFIER ::= { hpnicflswCommon 14 }
    hpnicfLswQosAclMib              OBJECT IDENTIFIER ::= { hpnicflswCommon 16 }
    hpnicfLswMix                    OBJECT IDENTIFIER ::= { hpnicflswCommon 17 }
    hpnicfLswDeviceAdmin            OBJECT IDENTIFIER ::= { hpnicflswCommon 18 }

END
