-- =============================================================
-- Copyright (c) 2010-2016 Hewlett-Packard Development Company, L.P.
--
-- Description: E1T1VI MIB
-- Reference:
-- Version: V1.3
-- History:
--   V1.0 2007-04-05 Initial Version by yandehan
--   V1.1 2009-06-08 modified by TONGWEI
--        Added hpnicfE1T1VIUsingTimeslotsRatio
--          and hpnicfE1T1VINotifications
--   V1.2 2010-04-08 modified by TONGWEI
--        Added hpnicfE1T1VIGeneral
--   V1.3 2015-08-19 modified by YUHAIYAN
--        Added hpnicfE1T1VITimeslotsUsedUpCount
--          and hpnicfE1T1VITimeslotSampleInterval
--          and hpnicfE1T1VIUsingTimeslotsPeak
--          and hpnicfE1T1VITrapTimeSlotsThreshold
--       Modified hpnicfE1T1VITrapTimeSlot
-- =============================================================
HPN-ICF-E1T1VI-MIB DEFINITIONS ::= BEGIN
    IMPORTS
        MODULE-IDENTITY, OBJECT-TYPE, Integer32, Unsigned32, NOTIFICATION-TYPE
            FROM SNMPv2-SMI
        ifIndex ,ifDescr
            FROM IF-MIB
        hpnicfCommon
            FROM HPN-ICF-OID-MIB;


-- =============================================================
-- E1T1VI Module
-- =============================================================
hpnicfE1T1VI MODULE-IDENTITY
    LAST-UPDATED    "201508191800Z"         -- Aug. 19, 2015 at 18:00 GMT
    ORGANIZATION
        ""
    CONTACT-INFO
        ""
    DESCRIPTION
        "This MIB provides E1/T1 voice interface information that are
        excluded by RFC 1213 and RFC 2233"
    REVISION        "201508191800Z"
    DESCRIPTION
        "Added hpnicfE1T1VITimeslotsUsedUpCount
         and hpnicfE1T1VITimeslotSampleInterval
         and hpnicfE1T1VIUsingTimeslotsPeak
         and hpnicfE1T1VITrapTimeSlotThreshold
         Modified hpnicfE1T1VITrapTimeSlot"
    REVISION        "201004081855Z"
    DESCRIPTION
        "To fix bugs in the MIB file."
    REVISION        "200906081741Z"
    DESCRIPTION
        "To fix bugs in the MIB file."
    REVISION        "200704051542Z"
    DESCRIPTION
        "Initial version of this MIB module."
    ::= { hpnicfCommon 76 }


hpnicfE1T1VITable OBJECT-TYPE
    SYNTAX      SEQUENCE OF HpnicfE1T1VIEntry
    MAX-ACCESS  not-accessible
    STATUS      current
    DESCRIPTION
        "This table contains E1/T1 voice interface information,
        such as the total number of using time slot."
    ::= { hpnicfE1T1VI 1 }

hpnicfE1T1VIEntry OBJECT-TYPE
    SYNTAX      HpnicfE1T1VIEntry
    MAX-ACCESS  not-accessible
    STATUS      current
    DESCRIPTION
        "This entry contains E1/T1 voice interface information.
        The index of this Entry is ifIndex defined in ifTable
        of RFC1213-MIB."
    INDEX
        {
            ifIndex
        }
    ::= { hpnicfE1T1VITable 1 }

HpnicfE1T1VIEntry ::= SEQUENCE
    {
        hpnicfE1T1VIUsingTimeslots    Integer32,
        hpnicfE1T1VIUsingTimeslotsRatio    Integer32,
        hpnicfE1T1VITimeslotsUsedUpCount    Unsigned32,
        hpnicfE1T1VITimeslotSampleInterval    Integer32,
        hpnicfE1T1VIUsingTimeslotsPeak    Integer32,
        hpnicfE1T1VITrapTimeSlotsThreshold    Integer32
    }

hpnicfE1T1VIUsingTimeslots OBJECT-TYPE
    SYNTAX      Integer32
    MAX-ACCESS  read-only
    STATUS      current
    DESCRIPTION
        "The total number of using time slots on this interface."
    ::= { hpnicfE1T1VIEntry 1 }

hpnicfE1T1VIUsingTimeslotsRatio OBJECT-TYPE
    SYNTAX      Integer32
    MAX-ACCESS  read-only
    STATUS      current
    DESCRIPTION
        "The total ratio of using time slots on this interface."
    ::= { hpnicfE1T1VIEntry 2 }

hpnicfE1T1VITimeslotsUsedUpCount OBJECT-TYPE
    SYNTAX      Unsigned32
    MAX-ACCESS  read-only
    STATUS      current
    DESCRIPTION
        "Total number of times that all time slots were used up on this interface."
    ::= { hpnicfE1T1VIEntry 3 }

hpnicfE1T1VITimeslotSampleInterval OBJECT-TYPE
    SYNTAX      Integer32
    MAX-ACCESS  read-write
    STATUS      current
    DESCRIPTION
        "Sampling interval in seconds for used time slots on this interface."
    ::= { hpnicfE1T1VIEntry 4 }

hpnicfE1T1VIUsingTimeslotsPeak OBJECT-TYPE
    SYNTAX      Integer32
    MAX-ACCESS  read-only
    STATUS      current
    DESCRIPTION
        "The peak number of used time slots in the entire sampling period on this interface."
    ::= { hpnicfE1T1VIEntry 5 }

hpnicfE1T1VITrapTimeSlotsThreshold OBJECT-TYPE
    SYNTAX      Integer32
    MAX-ACCESS  read-write
    STATUS      current
    DESCRIPTION
        "When the number of used time slots reaches the threshold, the hpnicfE1T1VITrapTimeSlot trap will
         be sent.  The valid range is from 1 to total number of time slots on the interface."
    ::= { hpnicfE1T1VIEntry 6 }


hpnicfE1T1VINotifications OBJECT IDENTIFIER ::= { hpnicfE1T1VI 2 }
hpnicfE1T1VITrapPrefix    OBJECT IDENTIFIER ::= { hpnicfE1T1VINotifications 0 }

hpnicfE1T1VITrapTimeSlot NOTIFICATION-TYPE
    OBJECTS { ifIndex, ifDescr }
    STATUS current
    DESCRIPTION
        "This trap is sent to the manager under the following
         condition: The number of used time slots of an E1/T1
         interface reaches the threshold."
    ::= { hpnicfE1T1VITrapPrefix 1 }

hpnicfE1T1VIGeneral  OBJECT IDENTIFIER ::= { hpnicfE1T1VI 3 }

hpnicfE1T1VITrapTimeSlotEnable OBJECT-TYPE
    SYNTAX  INTEGER {
            enable(1),
            disable(2)
        }
    MAX-ACCESS  read-write
    STATUS      current
    DESCRIPTION
        "This attribute controls whether the hpnicfE1T1VITrapTimeSlot trap will
        be sent or not."
    DEFVAL { enable }
    ::= { hpnicfE1T1VIGeneral 1 }

END
