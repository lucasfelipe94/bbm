-- ============================================================================
-- Copyright (c) 2010-2016 Hewlett-Packard Development Company, L.P.
--
-- Description: FAILOVER GROUP MIB
-- Reference:
-- Version: V1.0
-- History:
-- revision 1.0 2015-10-27 created by j03525
--
-- ============================================================================
HPN-ICF-FAILOVER-MIB DEFINITIONS ::= BEGIN

IMPORTS
    hpnicfCommon
        FROM HPN-ICF-OID-MIB
    Integer32, Unsigned32, OBJECT-TYPE, MODULE-IDENTITY, NOTIFICATION-TYPE
        FROM SNMPv2-SMI
    DisplayString, RowStatus
        FROM SNMPv2-TC;

hpnicfFailover MODULE-IDENTITY
    LAST-UPDATED "201510271040Z"
    ORGANIZATION
        ""
    CONTACT-INFO
        ""
    DESCRIPTION
        "This MIB file is to provide the definition of failover group.

        Such as:
        1. Configure Failover Groups for a device and display Failover Groups
           and their status.
        2. Assign CPU to the Failover Group, and display their status.

        Failover Group: A failover group contains a primary node and a secondary node.
        When a failover group is referenced by a service module, the primary node
        processes services and backs up service data to the secondary node.
        The secondary node does not process services, but it takes over the services
        when the primary node fails.
        When the primary node is recovered, traffic is switched to the primary node again."
    REVISION "201510271040Z"
    DESCRIPTION
        "The initial revision of this MIB module."
    ::= { hpnicfCommon 164 }


-- Node definitions

hpnicfFailoverScalarObjects OBJECT IDENTIFIER ::= { hpnicfFailover 1 }

hpnicfFailoverMaxNum OBJECT-TYPE
    SYNTAX Unsigned32
    MAX-ACCESS read-only
    STATUS current
    DESCRIPTION
        "The maximum number of Failover groups which the system supported to create, does not include the AutoBackup."
    ::= { hpnicfFailoverScalarObjects 1 }


hpnicfFailoverCurrentNum OBJECT-TYPE
    SYNTAX Unsigned32
    MAX-ACCESS read-only
    STATUS current
    DESCRIPTION
        "The current number of Failover groups which the system has created, does not include the AutoBackup."
    ::= { hpnicfFailoverScalarObjects 2 }


hpnicfFailoverTables OBJECT IDENTIFIER ::= { hpnicfFailover 2 }

hpnicfFailoverCfgTable OBJECT-TYPE
    SYNTAX SEQUENCE OF HpnicfFailoverCfgEntry
    MAX-ACCESS not-accessible
    STATUS current
    DESCRIPTION
        "This table is for configuration of backup group."
    ::= { hpnicfFailoverTables 1 }


hpnicfFailoverCfgEntry OBJECT-TYPE
    SYNTAX HpnicfFailoverCfgEntry
    MAX-ACCESS not-accessible
    STATUS current
    DESCRIPTION
        "An entry of the hpnicfFailoverGroupCfgTable."
    INDEX { hpnicfFailoverIndex }
    ::= { hpnicfFailoverCfgTable 1 }


HpnicfFailoverCfgEntry ::=
    SEQUENCE
    {
        hpnicfFailoverIndex
            Unsigned32,
        hpnicfFailoverName
            DisplayString,
        hpnicfFailoverPrimaryChassisID
            Integer32,
        hpnicfFailoverPrimarySlotID
            Integer32,
        hpnicfFailoverPrimaryCpuID
            Integer32,
        hpnicfFailoverSecondaryChassisID
            Integer32,
        hpnicfFailoverSecondarySlotID
            Integer32,
        hpnicfFailoverSecondaryCpuID
            Integer32,
        hpnicfFailoverState
            INTEGER,
        hpnicfFailoverRowStatus
            RowStatus
    }

hpnicfFailoverIndex OBJECT-TYPE
    SYNTAX Unsigned32 (0..4294967295)
    MAX-ACCESS accessible-for-notify
    STATUS current
    DESCRIPTION
        "Failover group ID is used as group index, the value range of failover group ID
        depends on the device model.
        The failover GroupIndex cannot be modified after creation."
    ::= { hpnicfFailoverCfgEntry 1 }


hpnicfFailoverName OBJECT-TYPE
    SYNTAX DisplayString (SIZE (1..63))
    MAX-ACCESS read-create
    STATUS current
    DESCRIPTION
        "Specifies the backup group name, a case-sensitive string of 1 to 63 characters.
        The failover group name cannot be modified after creation.
        The name can not include '?', and can not begin or end with ' '."
    ::= { hpnicfFailoverCfgEntry 2 }


hpnicfFailoverPrimaryChassisID OBJECT-TYPE
    SYNTAX Integer32 (-1..255)
    MAX-ACCESS read-create
    STATUS current
    DESCRIPTION
        "Specifies a card on an IRF member device.  The chassis-number argument represents
        the member ID of the IRF member device.  (Distributed devices In IRF mode.)
        On a centralized or distributed device, the value for this node is always zero.
        Note:The -1 for delete the node."
    ::= { hpnicfFailoverCfgEntry 3 }


hpnicfFailoverPrimarySlotID OBJECT-TYPE
    SYNTAX Integer32 (-1..255)
    MAX-ACCESS read-create
    STATUS current
    DESCRIPTION
        "Specifies a card by its slot number.  (Distributed devices In standalone mode.)
        Note:The -1 for delete the node."
    ::= { hpnicfFailoverCfgEntry 4 }


hpnicfFailoverPrimaryCpuID OBJECT-TYPE
    SYNTAX Integer32 (-1..7)
    MAX-ACCESS read-create
    STATUS current
    DESCRIPTION
        "Specifies a CPU by its number.  This option is available only if multiple CPUs
        are available on the specified slot.
        Note:The -1 for delete the node."
    ::= { hpnicfFailoverCfgEntry 5 }


hpnicfFailoverSecondaryChassisID OBJECT-TYPE
    SYNTAX Integer32 (-1..255)
    MAX-ACCESS read-create
    STATUS current
    DESCRIPTION
        "Specifies a card on an IRF member device.  The chassis-number argument represents
        the member ID of the IRF member device.  (Distributed devices In IRF mode.)
        On a centralized or distributed device, the value for this node is always zero.
        Note:The -1 for delete the node."
    ::= { hpnicfFailoverCfgEntry 6 }


hpnicfFailoverSecondarySlotID OBJECT-TYPE
    SYNTAX Integer32 (-1..255)
    MAX-ACCESS read-create
    STATUS current
    DESCRIPTION
        "Specifies a card by its slot number.  (Distributed devices In standalone mode.)
        Note:The -1 for delete the node."
    ::= { hpnicfFailoverCfgEntry 7 }


hpnicfFailoverSecondaryCpuID OBJECT-TYPE
    SYNTAX Integer32 (-1..7)
    MAX-ACCESS read-create
    STATUS current
    DESCRIPTION
        "Specifies a CPU by its number.  This option is available only if multiple CPUs
        are available on the specified slot.
        Note:The -1 for delete the node."
    ::= { hpnicfFailoverCfgEntry 8 }


hpnicfFailoverState OBJECT-TYPE
    SYNTAX INTEGER
        {
            initial(1),
            normal(2),
            fault(3)
        }
    MAX-ACCESS read-only
    STATUS current
    DESCRIPTION
        "Backup group state:
        Initial: No node in the failover group is processing services.
        Normal: The primary node is processing services.
        Fault: The secondary node is processing services."
    ::= { hpnicfFailoverCfgEntry 9 }


hpnicfFailoverRowStatus OBJECT-TYPE
    SYNTAX RowStatus
    MAX-ACCESS read-create
    STATUS current
    DESCRIPTION
        "The status of this table entry.
        Only support active(1), createAndGo(4) and destroy(6)."
    ::= { hpnicfFailoverCfgEntry 10 }

--
-- Notification definitions
--
-- =================================================================
-- Traps are defined below.
hpnicfFailoverNotification OBJECT IDENTIFIER ::= { hpnicfFailover 3 }

-- All objects used for TRAP only are defined here.
hpnicfFailoverTrap OBJECT IDENTIFIER ::= { hpnicfFailoverNotification 0 }

hpnicfFailoverCreate  NOTIFICATION-TYPE
    OBJECTS
        {
            hpnicfFailoverIndex,
            hpnicfFailoverName
        }

    STATUS current
    DESCRIPTION
        "The hpnicfFailoverCreate trap indicates that the failover group has created."
    ::= { hpnicfFailoverTrap 1 }

hpnicfFailoverDelete  NOTIFICATION-TYPE
    OBJECTS
        {
            hpnicfFailoverIndex,
            hpnicfFailoverName
        }
    STATUS current
    DESCRIPTION
        "The hpnicfFailoverDelete trap indicates that the failover group has deleted."
    ::= { hpnicfFailoverTrap 2 }

hpnicfFailoverPrimaryNodeAdd  NOTIFICATION-TYPE
    OBJECTS
        {
            hpnicfFailoverIndex,
            hpnicfFailoverName,
            hpnicfFailoverPrimaryChassisID,
            hpnicfFailoverPrimarySlotID,
            hpnicfFailoverPrimaryCpuID
        }
    STATUS current
    DESCRIPTION
        "The hpnicfFailoverPrimaryNodeAdd trap indicates that the failover group has
        added the primary node."
    ::= { hpnicfFailoverTrap 3 }

hpnicfFailoverPrimaryNodeRemove  NOTIFICATION-TYPE
    OBJECTS
        {
            hpnicfFailoverIndex,
            hpnicfFailoverName,
            hpnicfFailoverPrimaryChassisID,
            hpnicfFailoverPrimarySlotID,
            hpnicfFailoverPrimaryCpuID
        }
    STATUS current
    DESCRIPTION
        "The hpnicfFailoverPrimaryNodeRemove trap indicates that the failover group has
        removed the primary node."
    ::= { hpnicfFailoverTrap 4 }

hpnicfFailoverSecondaryNodeAdd  NOTIFICATION-TYPE
    OBJECTS
        {
            hpnicfFailoverIndex,
            hpnicfFailoverName,
            hpnicfFailoverSecondaryChassisID,
            hpnicfFailoverSecondarySlotID,
            hpnicfFailoverSecondaryCpuID
        }
    STATUS current
    DESCRIPTION
        "The hpnicfFailoverSecondaryNodeAdd trap indicates that the failover group has
        added the secondary node."
    ::= { hpnicfFailoverTrap 5 }

hpnicfFailoverSecondaryNodeRemove  NOTIFICATION-TYPE
    OBJECTS
        {
            hpnicfFailoverIndex,
            hpnicfFailoverName,
            hpnicfFailoverSecondaryChassisID,
            hpnicfFailoverSecondarySlotID,
            hpnicfFailoverSecondaryCpuID
        }
    STATUS current
    DESCRIPTION
        "The hpnicfFailoverSecondaryNodeRemove trap indicates that the failover group has
        removed the secondary node."
    ::= { hpnicfFailoverTrap 6 }

END
