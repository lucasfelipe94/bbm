-- =============================================================================
-- Copyright (c) 2010-2016 Hewlett-Packard Development Company, L.P.
--
-- Description: Multiprotocol Label Switching MIB
-- Reference:
-- Version: V1.2
-- History:
--   V1.0 2013-06-13 Initial version Created by Neng Yan
--   V1.1 2014-12-17 Modified by Neng Yan, Added hpnicfMplsExtBfdTable
--   V1.2 2015-06-16 Modified by Li Yun, Added hpnicfMplsExtVpnStatsTable
-- =============================================================================
HPN-ICF-MPLSEXT-MIB DEFINITIONS ::= BEGIN
IMPORTS
    MODULE-IDENTITY, OBJECT-TYPE, Unsigned32
        FROM SNMPv2-SMI
    RowStatus, TruthValue, DisplayString
        FROM SNMPv2-TC
    InetAddressType,InetAddress
        FROM INET-ADDRESS-MIB
    InterfaceIndexOrZero
        FROM IF-MIB
    hpnicfCommon
        FROM HPN-ICF-OID-MIB
    Counter64
        FROM SNMPv2-SMI
    ;

-- =============================================================================
-- module identity part
-- =============================================================================
hpnicfMplsExt MODULE-IDENTITY
    LAST-UPDATED
        "201506161800Z"   -- Jun 16, 2015 at 18:00 GMT
    ORGANIZATION
        ""
    CONTACT-INFO
        ""
    DESCRIPTION
        "Multiprotocol Label Switching MIB"
    REVISION
        "201506161800Z"   -- Jun 16, 2015 at 18:00 GMT
    DESCRIPTION
        "Added hpnicfMplsExtVpnStatsTable."
    REVISION
        "201412171200Z"   -- Dec 17, 2014 at 18:00 GMT
    DESCRIPTION
        "Added hpnicfMplsExtBfdTable."
    REVISION
        "201306131800Z"   -- Jan 13, 2013 at 18:00 GMT
    DESCRIPTION
        "Initial version of this MIB."
    ::= { hpnicfCommon 142 }

-- =============================================================================
-- object definition begin
-- =============================================================================
hpnicfMplsExtObjects      OBJECT IDENTIFIER ::= { hpnicfMplsExt 1 }

hpnicfMplsExtScalarGroup  OBJECT IDENTIFIER ::= { hpnicfMplsExtObjects 1 }

hpnicfMplsExtLsrID    OBJECT-TYPE
    SYNTAX      OCTET STRING (SIZE (0..32))
    MAX-ACCESS  read-write
    STATUS      current
    DESCRIPTION
        "The Label Switching Router's Identifier."
    ::= { hpnicfMplsExtScalarGroup 1 }

hpnicfMplsExtLdpStatus    OBJECT-TYPE
    SYNTAX      TruthValue
    MAX-ACCESS  read-write
    STATUS      current
    DESCRIPTION
        "The global configuration of Label Distribution Protocol(LDP)."
    ::= { hpnicfMplsExtScalarGroup 2 }

-- =============================================================================
-- hpnicfMplsExtTable Definition
-- =============================================================================
hpnicfMplsExtTable  OBJECT-TYPE
    SYNTAX      SEQUENCE OF HpnicfMplsExtEntry
    MAX-ACCESS  not-accessible
    STATUS      current
    DESCRIPTION
        "A table for configuring
        Multiprotocol Label Switching(MPLS) parameters."
    ::= { hpnicfMplsExtObjects 2 }

hpnicfMplsExtEntry   OBJECT-TYPE
    SYNTAX      HpnicfMplsExtEntry
    MAX-ACCESS  not-accessible
    STATUS      current
    DESCRIPTION
        "An entry for configuring MPLS parameters."
    INDEX
    {
        hpnicfMplsExtIndex
    }
    ::= { hpnicfMplsExtTable 1 }

HpnicfMplsExtEntry ::=
    SEQUENCE
    {
        hpnicfMplsExtIndex               Unsigned32,
        hpnicfMplsExtCapability          TruthValue,
        hpnicfMplsExtMtu                 Unsigned32,
        hpnicfMplsExtRowStatus           RowStatus
    }

hpnicfMplsExtIndex   OBJECT-TYPE
    SYNTAX      Unsigned32(1..4294967295)
    MAX-ACCESS  not-accessible
    STATUS      current
    DESCRIPTION
        "Index of MPLS interface."
    ::= { hpnicfMplsExtEntry 1 }

hpnicfMplsExtCapability    OBJECT-TYPE
    SYNTAX      TruthValue
    MAX-ACCESS  read-create
    STATUS      current
    DESCRIPTION
        "The MPLS capability of an interface."
    DEFVAL { false }
    ::= { hpnicfMplsExtEntry 2 }

hpnicfMplsExtMtu     OBJECT-TYPE
    SYNTAX      Unsigned32(46..65535)
    MAX-ACCESS  read-create
    STATUS      current
    DESCRIPTION
        "The MPLS Maximum Transmission Unit(MTU) of an interface."
    ::= { hpnicfMplsExtEntry 3 }

hpnicfMplsExtRowStatus     OBJECT-TYPE
    SYNTAX      RowStatus
    MAX-ACCESS  read-create
    STATUS      current
    DESCRIPTION
        "Operation status of this table entry."
    ::= { hpnicfMplsExtEntry 4 }
-- =============================================================================
-- End of hpnicfMplsExtTable Definition
-- =============================================================================

-- =============================================================================
-- hpnicfMplsExtLdpTable Definition
-- =============================================================================
hpnicfMplsExtLdpTable     OBJECT-TYPE
    SYNTAX      SEQUENCE OF HpnicfMplsExtLdpEntry
    MAX-ACCESS  not-accessible
    STATUS      current
    DESCRIPTION
        "A table for configuring LDP parameters."
    ::= { hpnicfMplsExtObjects 3 }

hpnicfMplsExtLdpEntry     OBJECT-TYPE
    SYNTAX      HpnicfMplsExtLdpEntry
    MAX-ACCESS  not-accessible
    STATUS      current
    DESCRIPTION
        "An entry for configuring LDP parameters."
    INDEX
    {
        hpnicfMplsExtLdpIndex
    }
    ::= { hpnicfMplsExtLdpTable 1 }

HpnicfMplsExtLdpEntry ::=
    SEQUENCE
    {
        hpnicfMplsExtLdpIndex                 Unsigned32,
        hpnicfMplsExtLdpCapability            TruthValue,
        hpnicfMplsExtLdpRowStatus             RowStatus
    }

hpnicfMplsExtLdpIndex     OBJECT-TYPE
    SYNTAX      Unsigned32(1..4294967295)
    MAX-ACCESS  not-accessible
    STATUS      current
    DESCRIPTION
        "Index of LDP interface."
    ::= { hpnicfMplsExtLdpEntry 1 }

hpnicfMplsExtLdpCapability    OBJECT-TYPE
    SYNTAX      TruthValue
    MAX-ACCESS  read-create
    STATUS      current
    DESCRIPTION
        "The LDP capability of an interface."
    DEFVAL { false }
    ::= { hpnicfMplsExtLdpEntry 2 }

hpnicfMplsExtLdpRowStatus     OBJECT-TYPE
    SYNTAX      RowStatus
    MAX-ACCESS  read-create
    STATUS      current
    DESCRIPTION
        "Operation status of this table entry.  A row entry cannot
        be modified when the value of this object is 'active'."
    ::= { hpnicfMplsExtLdpEntry 3 }
-- =============================================================================
-- End of hpnicfMplsExtLdpTable Definition
-- =============================================================================

-- =============================================================================
-- hpnicfMplsExtBfdTable Definition
-- =============================================================================
hpnicfMplsExtBfdTable  OBJECT-TYPE
    SYNTAX      SEQUENCE OF HpnicfMplsExtBfdEntry
    MAX-ACCESS  not-accessible
    STATUS      current
    DESCRIPTION
        "A table of MPLS Bidirectional Forwarding Detection(BFD) sessions."
    ::= { hpnicfMplsExtObjects 4 }

hpnicfMplsExtBfdEntry   OBJECT-TYPE
    SYNTAX      HpnicfMplsExtBfdEntry
    MAX-ACCESS  not-accessible
    STATUS      current
    DESCRIPTION
        "An entry in this table represents information on a single session."
    INDEX
    {
        hpnicfMplsExtBfdLocalDiscr
    }
    ::= { hpnicfMplsExtBfdTable 1 }

HpnicfMplsExtBfdEntry ::=
    SEQUENCE
    {
        hpnicfMplsExtBfdLocalDiscr            Unsigned32,
        hpnicfMplsExtBfdType                  INTEGER,
        hpnicfMplsExtBfdBindIfIndex           InterfaceIndexOrZero,
        hpnicfMplsExtBfdBindIfName            DisplayString,
        hpnicfMplsExtBfdXcIndex               OCTET STRING,
        hpnicfMplsExtBfdPwBackupFlag          INTEGER,
        hpnicfMplsExtBfdPwId                  Unsigned32,
        hpnicfMplsExtBfdVsiIndex              Unsigned32,
        hpnicfMplsExtBfdPwPeerIpType          InetAddressType,
        hpnicfMplsExtBfdPwPeerIp              InetAddress,
        hpnicfMplsExtBfdPwSPE                 INTEGER,
        hpnicfMplsExtBfdPwEncapType           INTEGER
    }

hpnicfMplsExtBfdLocalDiscr   OBJECT-TYPE
    SYNTAX      Unsigned32(1..4294967295)
    MAX-ACCESS  not-accessible
    STATUS      current
    DESCRIPTION
        "The local discriminator of the BFD session."
    ::= { hpnicfMplsExtBfdEntry 1 }

hpnicfMplsExtBfdType    OBJECT-TYPE
    SYNTAX      INTEGER {
                        unknown(1),
                        lsp(2),
                        vpwsPw(3),
                        vplsPw(4),
                        te(5)
                     }
    MAX-ACCESS  read-only
    STATUS      current
    DESCRIPTION
        "The type of the BFD session."
    ::= { hpnicfMplsExtBfdEntry 2 }

hpnicfMplsExtBfdBindIfIndex   OBJECT-TYPE
    SYNTAX      InterfaceIndexOrZero
    MAX-ACCESS  read-only
    STATUS      current
    DESCRIPTION
        "This object displays tunnel interface index when the value of
         hpnicfMplsExtBfdType is te(5), and displays interface index of
         an Attachment Circuit(AC) which is bound to a Pseudowire(PW) when
         the value of hpnicfMplsExtBfdType is vpwsPw(3).  This object is
         invalid when the value of hpnicfMplsExtBfdType is not te(5) or
         vpwsPw(3), then this object contains a zero value."
    ::= { hpnicfMplsExtBfdEntry 3 }

hpnicfMplsExtBfdBindIfName   OBJECT-TYPE
    SYNTAX      DisplayString (SIZE (0..255))
    MAX-ACCESS  read-only
    STATUS      current
    DESCRIPTION
        "This object displays tunnel interface name when the value of
         hpnicfMplsExtBfdType is te(5), and displays interface name of
         an AC which is bound to a PW when the value of hpnicfMplsExtBfdType
         is vpwsPw(3).  This object is invalid when the value of
         hpnicfMplsExtBfdType is not te(5) or vpwsPw(3), then this object
         contains a zero-length string."
    ::= { hpnicfMplsExtBfdEntry 4 }

hpnicfMplsExtBfdXcIndex   OBJECT-TYPE
    SYNTAX      OCTET STRING (SIZE (0..24))
    MAX-ACCESS  read-only
    STATUS      current
    DESCRIPTION
        "Primary index for MplsOutSegmentEntry.  This object is invalid when
        the value of hpnicfMplsExtBfdType is not lsp(2), then this object
        contains a zero-length string."
    ::= { hpnicfMplsExtBfdEntry 5 }

hpnicfMplsExtBfdPwBackupFlag     OBJECT-TYPE
    SYNTAX      INTEGER {
                        none(1),
                        primary(2),
                        backup(3)
                     }
    MAX-ACCESS  read-only
    STATUS      current
    DESCRIPTION
        "PW flag."
    ::= { hpnicfMplsExtBfdEntry 6 }

hpnicfMplsExtBfdPwId     OBJECT-TYPE
    SYNTAX      Unsigned32(0..4294967295)
    MAX-ACCESS  read-only
    STATUS      current
    DESCRIPTION
        "PW Identifier."
    DEFVAL { 0 }
    ::= { hpnicfMplsExtBfdEntry 7 }

hpnicfMplsExtBfdVsiIndex     OBJECT-TYPE
    SYNTAX      Unsigned32(1..4294967295)
    MAX-ACCESS  read-only
    STATUS      current
    DESCRIPTION
        "Virtual Switch Instance(VSI) index."
    DEFVAL { 4294967295 }
    ::= { hpnicfMplsExtBfdEntry 8 }

hpnicfMplsExtBfdPwPeerIpType     OBJECT-TYPE
    SYNTAX      InetAddressType
    MAX-ACCESS  read-only
    STATUS      current
    DESCRIPTION
        "The type of peer address.  Typically, this
        address type is IPv4 or IPv6, with a prefix length
        of 32 or 128, respectively."
    ::= { hpnicfMplsExtBfdEntry 9 }

hpnicfMplsExtBfdPwPeerIp     OBJECT-TYPE
    SYNTAX      InetAddress
    MAX-ACCESS  read-only
    STATUS      current
    DESCRIPTION
        "Peer address of the PW."
    ::= { hpnicfMplsExtBfdEntry 10 }

hpnicfMplsExtBfdPwSPE     OBJECT-TYPE
    SYNTAX      INTEGER {
                        none(1),
                        upe(2),
                        spe(3)
                     }
    MAX-ACCESS  read-only
    STATUS      current
    DESCRIPTION
        "Node information of the Virtual Private Wire Service(VPWS) PW,
        User facing-Provider Edge(UPE) or Switching Provider Edge(SPE)."
    ::= { hpnicfMplsExtBfdEntry 11 }

hpnicfMplsExtBfdPwEncapType     OBJECT-TYPE
    SYNTAX      INTEGER {
                        unknown(1),
                        frDlciMartini(2),
                        atmAal5Sdu(3),
                        atmTransCell(4),
                        vlan(5),
                        ethernet(6),
                        hdlc(7),
                        ppp(8),
                        cesom(9),
                        atmNto1Vcc(10),
                        atmNto1Vpc(11),
                        ipInterworking(12),
                        atm1to1Vcc(13),
                        atm1to1Vpc(14),
                        atmAal5Pdu(15),
                        frPort(16),
                        cep(17),
                        satopE1(18),
                        satopT1(19),
                        satopE3(20),
                        satopT3(21),
                        esopsnBasic(22),
                        tdmoipAal1Mode(23),
                        tdmCesopsnWithCas(24),
                        tdmoipAal2Mode(25),
                        frDlci(26)
                     }
    MAX-ACCESS  read-only
    STATUS      current
    DESCRIPTION
        "Encapsulation type of the PW."
    ::= { hpnicfMplsExtBfdEntry 12 }
-- =============================================================================
-- End of hpnicfMplsExtBfdTable Definition
-- =============================================================================

-- =============================================================================
-- hpnicfMplsExtVpnStatsTable Definition
-- =============================================================================
hpnicfMplsExtVpnStatsTable  OBJECT-TYPE
    SYNTAX      SEQUENCE OF HpnicfMplsExtVpnStatsEntry
    MAX-ACCESS  not-accessible
    STATUS      current
    DESCRIPTION
        "A table contains statistical information about packets
         received from and sent by each VPN."
    ::= { hpnicfMplsExtObjects 5 }

hpnicfMplsExtVpnStatsEntry   OBJECT-TYPE
    SYNTAX      HpnicfMplsExtVpnStatsEntry
    MAX-ACCESS  not-accessible
    STATUS      current
    DESCRIPTION
        "An entry in this table contains statistical
        information about packets received from and sent by a VPN."
    INDEX
    {
        hpnicfMplsExtVpnStatsVrfIndex
    }
    ::= { hpnicfMplsExtVpnStatsTable 1 }

HpnicfMplsExtVpnStatsEntry ::=
    SEQUENCE
    {
        hpnicfMplsExtVpnStatsVrfIndex            Unsigned32,
        hpnicfMplsExtVpnStatsVpnName             OCTET STRING,
        hpnicfMplsExtVpnStatsInOctets            Counter64,
        hpnicfMplsExtVpnStatsInPackets           Counter64,
        hpnicfMplsExtVpnStatsInErrors            Counter64,
        hpnicfMplsExtVpnStatsInDiscards          Counter64,
        hpnicfMplsExtVpnStatsOutOctets           Counter64,
        hpnicfMplsExtVpnStatsOutPackets          Counter64,
        hpnicfMplsExtVpnStatsOutErrors           Counter64,
        hpnicfMplsExtVpnStatsOutDiscards         Counter64
    }

hpnicfMplsExtVpnStatsVrfIndex   OBJECT-TYPE
    SYNTAX      Unsigned32(1..4294967295)
    MAX-ACCESS  not-accessible
    STATUS      current
    DESCRIPTION
        "The index of a VPN."
    ::= { hpnicfMplsExtVpnStatsEntry 1 }

hpnicfMplsExtVpnStatsVpnName   OBJECT-TYPE
    SYNTAX      OCTET STRING (SIZE (1..31))
    MAX-ACCESS  read-only
    STATUS      current
    DESCRIPTION
        "The name of a VPN."
    ::= { hpnicfMplsExtVpnStatsEntry 2 }

hpnicfMplsExtVpnStatsInOctets     OBJECT-TYPE
    SYNTAX      Counter64
    MAX-ACCESS  read-only
    STATUS      current
    DESCRIPTION
        "Number of octets received from a VPN."
    ::= { hpnicfMplsExtVpnStatsEntry 3 }

hpnicfMplsExtVpnStatsInPackets   OBJECT-TYPE
    SYNTAX      Counter64
    MAX-ACCESS  read-only
    STATUS      current
    DESCRIPTION
        "Number of packets received from a VPN."
    ::= { hpnicfMplsExtVpnStatsEntry 4 }

hpnicfMplsExtVpnStatsInErrors     OBJECT-TYPE
    SYNTAX      Counter64
    MAX-ACCESS  read-only
    STATUS      current
    DESCRIPTION
        "Number of error packets received from a VPN."
    ::= { hpnicfMplsExtVpnStatsEntry 5 }

hpnicfMplsExtVpnStatsInDiscards   OBJECT-TYPE
    SYNTAX      Counter64
    MAX-ACCESS  read-only
    STATUS      current
    DESCRIPTION
        "Number of incoming packets,
        which were chosen to be discarded by a VPN even
        though no errors had been detected to prevent their
        being transmitted."
    ::= { hpnicfMplsExtVpnStatsEntry 6 }

hpnicfMplsExtVpnStatsOutOctets     OBJECT-TYPE
    SYNTAX      Counter64
    MAX-ACCESS  read-only
    STATUS      current
    DESCRIPTION
        "Number of octets sent by a VPN."
    ::= { hpnicfMplsExtVpnStatsEntry 7 }

hpnicfMplsExtVpnStatsOutPackets     OBJECT-TYPE
    SYNTAX      Counter64
    MAX-ACCESS  read-only
    STATUS      current
    DESCRIPTION
        "Number of packets sent by a VPN."
    ::= { hpnicfMplsExtVpnStatsEntry 8 }

hpnicfMplsExtVpnStatsOutErrors     OBJECT-TYPE
    SYNTAX      Counter64
    MAX-ACCESS  read-only
    STATUS      current
    DESCRIPTION
        "Number of packets that could not be sent by a VPN
        due to errors."
    ::= { hpnicfMplsExtVpnStatsEntry 9 }

hpnicfMplsExtVpnStatsOutDiscards     OBJECT-TYPE
    SYNTAX      Counter64
    MAX-ACCESS  read-only
    STATUS      current
    DESCRIPTION
        "Number of outgoing packets which were chosen to be discarded
        by a VPN even though no errors had been detected to prevent
        their being transmitted.  One possible reason for
        discarding such a packet could be to free up
        buffer space."
    ::= { hpnicfMplsExtVpnStatsEntry 10 }

-- =============================================================================
-- End of hpnicfMplsExtVpnStatsTable Definition
-- =============================================================================

END
