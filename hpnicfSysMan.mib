-- ===========================================================================================================
-- Copyright (c) 2010-2016 Hewlett-Packard Development Company, L.P.
--
-- Description: System Management MIB
-- Reference:
-- Version: V2.6
-- History:
--  revision 1.0 2002-12-20 created by xuqingwei
--  revision 1.1 2004-4-16  added the support for XRN  by xuqingwei
--  revision 1.2 2004-4-16  added 'hpnicfSysImageType' in hpnicfSysImageTable for dual image  by changxiangqing
--  revision 1.3 2004-5-14  convert MIB object name from hpnicfXXX to hpnicf, etc.
--  revision 1.31 2004-7-16 1. modified 'hpnicfSysImageSize' in hpnicfSysImageTable by zhaolina
--                      2.modified SYNTAX of 'hpnicfSysReloadImage','hpnicfSysImageIndex','hpnicfSysCFGFileIndex'
--                           from (1..2147483647) to (0..2147483647) by zhaolina
--  revision 1.5 2004-8-1  1. added 'secure' attribute for hpnicfSysImageType in hpnicfSysImageTable by zhaolina
--                         2.modified 'MAX-ACCESS' of hpnicfSysReloadTag from 'read-create' to 'read-write' by zhaolina
--                         3.modified DESCRIPTION of hpnicfSysReloadNotification by zhaolina
--                         4.modified DESCRIPTION of hpnicfSysImageType,hpnicfSysImageIndex,hpnicfSysImageTable and hpnicfSysReloadImage by zhaolina
--  revision 1.6 2004-9-8  1.modified DESCRIPTION of hpnicfSysImageType by wangyingxia
--                         2.added the trap object hpnicfSysStartUpNotification by wangyingxia
--                         3.added hpnicfSysStartUpNotification into the NOTIFICATION OF hpnicfSystemManMIBNotifications
--  revision 1.7 2004-10-12 updated by gaolong
--               Change all underscore('_') characters to hyphen characters('-') because underscore character is not allowed in MIB module.
--               Remove hpnicfSysCurEntPhysicalIndex from hpnicfSysCurGroup because this object is not accessible.
--  revision 1.8 2004-11-08 Change the description of hpnicfSysReloadScheduleIndex by gaolong
--  revision 1.9 2005-04-08 updated by songjie.
--               1. added the support of summer time.
--               2. correct word errors and adjust file format.
--  revision 2.0 2005-12-26 updated by jinyi
--               added hpnicfSysCurBtmFileName, hpnicfSysCurUpdateBtmFileName,
--               hpnicfSysBtmLoadMaxNumber, and hpnicfSysBtmLoadTable.
--  revision 2.1 2006-04-03 updated by shuaixiaojuan
--               modified descriptions of some objects.
--  revision 2.2 2009-06-07 Change the MAX-ACCESS of hpnicfSysLocalClock.
--          V2.3 2010-03-17 add hpnicfSysLocalClockString by jinyi
--  revision V2.4 2011-08-30 add  hpnicfSysPackage, hpnicfSysIpePackage by z02031
--  revision V2.5 2013-10-18 add hpnicfSysPackageLoadAttribute, hpnicfSysPackageModel, hpnicfSysIpeFileModel,
--                hpnicfSysIpePackageModel and hpnicfSysSetBootImage by z03030 and z08715
--  revision V2.6 2015-07-07 add hpnicfSysClockProtocolGroup, hpnicfSysClockProtocol, hpnicfSysClockProtocolSrcMdc
--                and hpnicfSysClockProtocolSrcContext by l09650
-- ============================================================================================================
HPN-ICF-SYS-MAN-MIB DEFINITIONS ::= BEGIN

IMPORTS
    OBJECT-GROUP, MODULE-COMPLIANCE, NOTIFICATION-GROUP
        FROM SNMPv2-CONF
    Integer32, OBJECT-TYPE, MODULE-IDENTITY, NOTIFICATION-TYPE, TimeTicks, Unsigned32
        FROM SNMPv2-SMI
    DateAndTime, DisplayString, RowStatus, TruthValue
        FROM SNMPv2-TC
    SnmpTagList, SnmpTagValue
        FROM SNMP-TARGET-MIB
    hpnicfCommon
        FROM HPN-ICF-OID-MIB;


hpnicfSystemMan MODULE-IDENTITY
    LAST-UPDATED "201507270000Z"
    ORGANIZATION
        ""
    CONTACT-INFO
        ""
    DESCRIPTION
        "This MIB contains objects to manage the system.
         It focuses on the display of current configure file and image
         file,and the definition of reloading image.
         Add the support for XRN."
    REVISION     "201507270000Z"
    DESCRIPTION  "Add hpnicfSysClockProtocolGroup, hpnicfSysClockProtocol, hpnicfSysClockProtocolSrcMdc
--                and hpnicfSysClockProtocolSrcContext by l09650."
    REVISION "200404081345Z"        -- April 08, 2004 at 13:45 GMT
    DESCRIPTION
        " "
    ::= { hpnicfCommon 3 }


-- XRN brief introduction:
--    Expandable resilient networking (XRN) is a technology to construct expandable
--    resilient networks. With XRN feature, you can connect several devices into a
--    combined device and treat them as a single one. The combined device is called
--    Fabric, while the member devices are units.




--
-- Node definitions
--

hpnicfSystemManMIBObjects OBJECT IDENTIFIER ::= { hpnicfSystemMan 1 }


hpnicfSysClock OBJECT IDENTIFIER ::= { hpnicfSystemManMIBObjects 1 }

hpnicfSysLocalClock OBJECT-TYPE
    SYNTAX DateAndTime
    MAX-ACCESS read-write
    STATUS current
    DESCRIPTION
        "
        This node gives the current local time of the system.
        The unit of it is DateAndTime.
        "
    ::= { hpnicfSysClock 1 }

hpnicfSysSummerTime OBJECT IDENTIFIER ::= { hpnicfSysClock 2 }

hpnicfSysSummerTimeEnable OBJECT-TYPE
    SYNTAX INTEGER
    {
        enable(1),
        disable(2)
    }
    MAX-ACCESS read-only
    STATUS current
    DESCRIPTION
        "This node indicates the status of summer time.
        If the value of this node is enable, means that summer time is
        enabled.
        If the value is disable, means that summer time is disabled.
        "
    ::= { hpnicfSysSummerTime 1 }

hpnicfSysSummerTimeZone OBJECT-TYPE
    SYNTAX DisplayString (SIZE (0..255))
    MAX-ACCESS read-write
    STATUS current
    DESCRIPTION
        "
        This node describes the name of time zone in summer.
        The string is only used to display in local time when summer
        time is running.
        That the value of hpnicfSysLocalClock has the time zone information
        means that summer time is running.
        "
    ::= { hpnicfSysSummerTime 2 }

hpnicfSysSummerTimeMethod OBJECT-TYPE
    SYNTAX INTEGER
    {
        oneOff(1),
        repeating(2)
    }
    MAX-ACCESS read-write
    STATUS current
    DESCRIPTION
        "
        This node provides the execute method of summer time.
        oneOff(1):   means that summer time only takes effect at specified time.
        repeating(2): means that summer time takes effect in specified month/day
                      once a year.
        "
    ::= { hpnicfSysSummerTime 3 }

hpnicfSysSummerTimeStart OBJECT-TYPE
    SYNTAX DateAndTime (SIZE(8))
    MAX-ACCESS read-write
    STATUS current
    DESCRIPTION
        "
        This node provides the start time of summer time.
        "
    ::= { hpnicfSysSummerTime 4 }

hpnicfSysSummerTimeEnd OBJECT-TYPE
    SYNTAX DateAndTime (SIZE(8))
    MAX-ACCESS read-write
    STATUS current
    DESCRIPTION
        "
        This node provides the end time of summer time.
        The end time must be more than start time one day and less
        than start time one year.
        "
    ::= { hpnicfSysSummerTime 5 }

hpnicfSysSummerTimeOffset OBJECT-TYPE
    SYNTAX Integer32 (0..86399)
    MAX-ACCESS read-write
    STATUS current
    DESCRIPTION
        "
        This node provides the offset time of summer time.
        The offset time(in seconds) means that how much time need to be
        appended to the local time.
        "
    ::= { hpnicfSysSummerTime 6 }

hpnicfSysLocalClockString OBJECT-TYPE
    SYNTAX OCTET STRING(SIZE (16..24))
    MAX-ACCESS read-write
    STATUS current
    DESCRIPTION
        "This node gives the current local time of the system.
        For example, Tuesday May 26, 2002 at 1:30:15 would be
        displayed as: 2002-5-26T13:30:15.0Z"
    ::= { hpnicfSysClock 3 }

hpnicfSysClockProtocolGroup OBJECT IDENTIFIER ::= { hpnicfSysClock 4 }

hpnicfSysClockProtocol OBJECT-TYPE
    SYNTAX INTEGER
        {
        none(1),
        ntp(2),
        ptp(3)
         }
    MAX-ACCESS read-write
    STATUS current
    DESCRIPTION
        "Writing none(1) to this object indicates to use the local system time.
        When the value is set to none(1), hpnicfSysClockProtocolSrcMdc and
        hpnicfSysClockProtocolSrcContext cannot be written and the value will be
        set to invalid.  Change system time will be performed through the node
        of hpnicfSysLocalClock and hpnicfSysSummerTime.
        Writing ntp(2) to this object indicates to use NTP time source.
        NTP means Network Time Protocol.  To get the system time through NTP,
        NTP must be configured successfully.  NTP time source can be obtained
        from non-default MDC and non-default context.
        When ntp(2) is set, the system time can't be changed manually.
        Support for this keyword depends on the device model.

        Writing ptp(3) to this object indicates to use PTP time source.
        PTP means Precision Time Protocol.  To get clock time through PTP, PTP
        must be configured successfully.  PTP time source can be obtained from
        non-default MDC but cannot be obtained from non-default context.
        When ptp(3) is set, the system time can't be changed manually.
        Support for this keyword depends on the device model.

        All MDCs on the device share the same time source and use the same system time.
        The shared time source can be one of the following items:
        Local system time - the time signal that is generated by the local
        crystal oscillator
        Remote time source - the time signal that is obtained by the specified MDC
        from another device on the network."
    ::= { hpnicfSysClockProtocolGroup 1 }

hpnicfSysClockProtocolSrcMdc OBJECT-TYPE
    SYNTAX Integer32 (0..2147483647)
    MAX-ACCESS read-write
    STATUS current
    DESCRIPTION
        "The MDC ID that is used for the system time source.
        This node is valid when the clock protocol is NTP or PTP.
        If MDC is not supported on this system, this node is invalid.
        If the device supports MDC, the system time will be obtained
        from NTP or PTP on the specified MDC.
        If the device supports context and MDC, the most recent configuration of
        hpnicfSysClockProtocolSrcContext and hpnicfSysClockProtocolSrcMdc takes
        effect if set multiple times, and another one will be set to zero as an
        invalid value."
     DEFVAL { 1 }
    ::= { hpnicfSysClockProtocolGroup 2 }

hpnicfSysClockProtocolSrcContext OBJECT-TYPE
    SYNTAX Integer32 (0..2147483647)
    MAX-ACCESS read-write
    STATUS current
    DESCRIPTION
        "The context ID that is used for the system time source.
        This node is valid when the clock protocol is NTP or PTP.
        If context is not supported on this system, this node is invalid.
        If the system supports context, the system time will be obtained from
        NTP or PTP on the specified context.
        If the device supports context and MDC, the most recent configuration of
        hpnicfSysClockProtocolSrcContext and hpnicfSysClockProtocolSrcMdc takes
        effect if set multiple times, and another one will be set to zero as an
        invalid value."
    DEFVAL { 1 }
    ::= { hpnicfSysClockProtocolGroup 3 }

hpnicfSysCurrent OBJECT IDENTIFIER ::= { hpnicfSystemManMIBObjects 2 }

hpnicfSysCurTable OBJECT-TYPE
    SYNTAX SEQUENCE OF HpnicfSysCurEntry
    MAX-ACCESS not-accessible
    STATUS current
    DESCRIPTION
        "
        The current status of system. A configuration file, an image
        file and bootrom information are used to describe the current status.
        "
    ::= { hpnicfSysCurrent 1 }

hpnicfSysCurEntry OBJECT-TYPE
    SYNTAX HpnicfSysCurEntry
    MAX-ACCESS not-accessible
    STATUS current
    DESCRIPTION
        "
        An entry of hpnicfSysCurTable.
        "
    INDEX { hpnicfSysCurEntPhysicalIndex }
    ::= { hpnicfSysCurTable 1 }

HpnicfSysCurEntry ::=
    SEQUENCE {
        hpnicfSysCurEntPhysicalIndex       Integer32,
        hpnicfSysCurCFGFileIndex           Integer32,
        hpnicfSysCurImageIndex             Integer32,
        hpnicfSysCurBtmFileName            OCTET STRING,
        hpnicfSysCurUpdateBtmFileName      OCTET STRING
     }

hpnicfSysCurEntPhysicalIndex OBJECT-TYPE
    SYNTAX Integer32 (0..2147483647)
    MAX-ACCESS not-accessible
    STATUS current
    DESCRIPTION
        "The value of this object is the entity index
         which depends on the implementation of ENTITY-MIB.
         If ENTITY-MIB is not supported, the value for this object is the unit ID for XRN devices ,
         0 for non-XRN device which has only one mainboard,
         the board number for non-XRN device which have several mainboards.
        "
    ::= { hpnicfSysCurEntry 1 }

hpnicfSysCurCFGFileIndex OBJECT-TYPE
    SYNTAX Integer32 (0..2147483647)
    MAX-ACCESS read-only
    STATUS current
    DESCRIPTION
        "
        The startup configuration file currently used by the specified entity.
        If the value of it is zero, no configuration file is used. It will be
        the value of corresponding hpnicfSysCFGFileIndex in hpnicfSysCFGFileTable.
        "
    ::= { hpnicfSysCurEntry 2 }

hpnicfSysCurImageIndex OBJECT-TYPE
    SYNTAX Integer32 (0..2147483647)
    MAX-ACCESS read-only
    STATUS current
    DESCRIPTION
        "The image file currently used by the specified entity.
        It will be the value of corresponding hpnicfSysImageIndex
        in hpnicfSysImageTable."
    ::= { hpnicfSysCurEntry 3 }

hpnicfSysCurBtmFileName OBJECT-TYPE
    SYNTAX OCTET STRING(SIZE (1..64))
    MAX-ACCESS read-only
    STATUS current
    DESCRIPTION
        "The bootrom file currently used by the specified entity."
    ::= { hpnicfSysCurEntry 4 }

hpnicfSysCurUpdateBtmFileName OBJECT-TYPE
    SYNTAX OCTET STRING(SIZE (1..64))
    MAX-ACCESS read-only
    STATUS current
    DESCRIPTION
        "
        The default value of this object is the same as the value of
        hpnicfSysCurBtmFileName. The value will be changed after updating
        the bootrom successfully. This bootrom will take effect on next
        startup.
        "
    ::= { hpnicfSysCurEntry 5 }

-- Begin define reload group
hpnicfSysReload OBJECT IDENTIFIER ::= { hpnicfSystemManMIBObjects 3 }

hpnicfSysReloadSchedule OBJECT-TYPE
    SYNTAX Integer32 (0..2147483647)
    MAX-ACCESS read-write
    STATUS current
    DESCRIPTION
        "
        The object points one row in hpnicfSysReloadScheduleTable.
        Its value is equal to the value of hpnicfSysReloadScheduleIndex.
        When a reload action is finished, the value of it
        would be zero which means no any reload schedule is selected.
        "
    ::= { hpnicfSysReload 1 }

hpnicfSysReloadAction OBJECT-TYPE
    SYNTAX INTEGER
        {
        reloadUnavailable(1),
        reloadOnSchedule(2),
        reloadAtOnce(3),
        reloadCancel(4)
        }
    MAX-ACCESS read-write
    STATUS current
    DESCRIPTION
        "
        Writing reloadOnSchedule(2) to this object performs the reload operation on schedule.
        If hpnicfSysReloadScheduleTime is not set, the value of hpnicfSysReloadAction can't be set to
        'reloadOnSchedule(2)'.

        Writing reloadAtOnce(3)to this object performs the reload operation at once,
        regardless of the hpnicfSysReloadScheduleTime.

        When reloadCancel(4)is set, the scheduled reload action will be cancelled and the value of
        hpnicfSysReloadAction will be 'reloadUnavailable(1)',the value of hpnicfSysReloadSchedule will be
        0, hpnicfSysReloadTag will be given a value of zero length, but the content of
        hpnicfSysReloadScheduleTable will remain.


        The hpnicfSysReloadSchedule and hpnicfSysReloadTag  determine the reload entity(ies) in mutually
        exclusive way. And the hpnicfSysReloadSchedule will be handled at first. If the value of
        hpnicfSysReloadSchedule is invalid, then the hpnicfSysReloadTag will be handled.

        If the value of hpnicfSysReloadSchedule is valid, the value of hpnicfSysReloadTag is ignored and a
        reload action will be implemented to the entity specified by hpnicfSysReloadEntity in the entry
        pointed by hpnicfSysReloadSchedule.

        If hpnicfSysReloadSchedule is valid, but the entry hpnicfSysReloadSchedule pointing to is not active,
        the reload action will be ignored , and an inconsistent value will be returned.


        If multiple entities are required to be reloaded at the same time, the value of hpnicfSysReloadTag
        must be specified to select the reload parameters in the hpnicfSysReloadSceduelTable, and
        hpnicfSysReloadSchedule must have the value of '0'.

        If the whole fabric is to be reloaded in an XRN device, all the units in the fabric must
        have at least one entry in the hpnicfSysReloadSceduelTable with the same tag in hpnicfSysReloadSceduelTagList.

        When a reload action is done, or there is no reload action, the value
        should be reloadUnavailable(1).
        "
    ::= { hpnicfSysReload 2 }

hpnicfSysReloadScheduleTable OBJECT-TYPE
    SYNTAX SEQUENCE OF HpnicfSysReloadScheduleEntry
    MAX-ACCESS not-accessible
    STATUS current
    DESCRIPTION
        "
        A reload parameters set table.

        The table is exclusively used for reloading.

        When reloading action finished, the value of the table may be empty or still exist.
        If the mainboard in non-XRN device or all the units of the fabric in XRN device are
        reloaded,then the table will be refreshed.
        "
    ::= { hpnicfSysReload 3 }

hpnicfSysReloadScheduleEntry OBJECT-TYPE
    SYNTAX HpnicfSysReloadScheduleEntry
    MAX-ACCESS not-accessible
    STATUS current
    DESCRIPTION
        "Entry of hpnicfSysReloadScheduleTable."
    INDEX { hpnicfSysReloadScheduleIndex }
    ::= { hpnicfSysReloadScheduleTable 1 }

HpnicfSysReloadScheduleEntry ::=
    SEQUENCE {
        hpnicfSysReloadScheduleIndex           Integer32,
        hpnicfSysReloadEntity                  Integer32,
        hpnicfSysReloadCfgFile                 Integer32,
        hpnicfSysReloadImage                   Integer32,
        hpnicfSysReloadReason                  DisplayString,
        hpnicfSysReloadScheduleTime            DateAndTime,
        hpnicfSysReloadRowStatus               RowStatus,
        hpnicfSysReloadScheduleTagList         SnmpTagList
     }

hpnicfSysReloadScheduleIndex OBJECT-TYPE
    SYNTAX Integer32 (1..2147483647)
    MAX-ACCESS not-accessible
    STATUS current
    DESCRIPTION
        "The index of hpnicfSysReloadScheduleTable. There are two parts
        for this index depicted as follows:

        31                  15                  0
        +++++++++++++++++++++++++++++++++++++++++
        + physical index     +     random index +
        ( bit 16..31 )              ( bit 0..15 )
        +++++++++++++++++++++++++++++++++++++++++
        From bit0 to bit15 (two bytes), if the row is automatic created,
        the value is zero, and if the row is created by users, then the
        value is determined by the users.

        From bit16 to bit31 (two bytes) is the physical index the same as the
        entPhysicalIndex specified in ENTITY-MIB. For XRN devices,
        physical index is the value of a chassis entPhysicalIndex. 0 for non-XRN
        device which has only one main board, the board number for non-XRN device
        which have multiple main boards."
    ::= { hpnicfSysReloadScheduleEntry 1 }

hpnicfSysReloadEntity OBJECT-TYPE
    SYNTAX Integer32 (0..2147483647)
    MAX-ACCESS read-create
    STATUS current
    DESCRIPTION
        "
        The value of hpnicfSysReloadEntity indicates an entry in entPhysicalTable,
        which is the physical entity to be reloaded.

        If ENTITY-MIB is not supported,the value for this object is the unit ID for XRN devices ,
        0 for non-XRN device which has only one mainboard,
        the board number for non-XRN device which have several mainboards.

        Each entity has only one row in hpnicfSysReloadScheduleTable.
        "
    ::= { hpnicfSysReloadScheduleEntry 2 }

hpnicfSysReloadCfgFile OBJECT-TYPE
    SYNTAX Integer32 (0..2147483647)
    MAX-ACCESS read-create
    STATUS current
    DESCRIPTION
        "
        The value indicates an entry in hpnicfSysCFGFileTable.
        It defines a configuration file for reload action.
        It is the value of corresponding hpnicfSysCFGFileIndex in hpnicfSysCFGFileTable.
        The zero value means no configuration file has been set for this entry, and
        no configuration file is used during system reloading.
        "
    ::= { hpnicfSysReloadScheduleEntry 3 }

hpnicfSysReloadImage OBJECT-TYPE
    SYNTAX Integer32 (0..2147483647)
    MAX-ACCESS read-create
    STATUS current
    DESCRIPTION
        "
        The value indicates an entry in hpnicfSysImageTable.
        It defines an image file for reload action.
        It is the value of corresponding hpnicfSysImageIndex in hpnicfSysImageTable.

        If dual image is supported, the main image attribute can be
        set through this object or by hpnicfSysImageType of hpnicfSysImageTable
        of the entity. It is strongly suggested to set this attribute by
        the latter.

        If main image attribute is set here, the hpnicfSysImageType in hpnicfSysImageTable
        of the corresponding entity will be updated, and vice versa.

        Before reboot, the device will check the validation of the entry. If the file does
        not exist, the device will not reboot and a trap will be send to NMS.
        "
    ::= { hpnicfSysReloadScheduleEntry 4 }

hpnicfSysReloadReason OBJECT-TYPE
    SYNTAX DisplayString (SIZE (0..255))
    MAX-ACCESS read-create
    STATUS current
    DESCRIPTION
        "
        The reason of system's reloading.
        It is a zero length octet string when not set.
        "
    ::= { hpnicfSysReloadScheduleEntry 5 }

hpnicfSysReloadScheduleTime OBJECT-TYPE
    SYNTAX DateAndTime (SIZE(8))
    MAX-ACCESS read-create
    STATUS current
    DESCRIPTION
        "
        Specify the local time at which the reload action will
        occur. we will only take octet strings
        with length 8 for this object which indicates the
        local time of the switch. The maximum scheduled
        interval between the specified time and the current
        system clock time is 24 days .

            field  octets  contents                  range
            -----  ------  --------                  -----
              1      1-2   year                      0..65536
              2       3    month                     1..12
              3       4    day                       1..31
              4       5    hour                      0..23
              5       6    minutes                   0..59
              6       7    seconds                   0..60

         For example, Tuesday May 26, 1992 at 1:30:15 PM would be
         displayed as:

                    1992-5-26,13:30:15

        If the set value is less than the value of hpnicfSysLocalClock
        or beyond the maximum scheduled time limit, a bad value error
        occurred.
        The value of all-zero octet strings indicates system reload
        at once if the reload action is reloadOnSchedule(2).
        "
    ::= { hpnicfSysReloadScheduleEntry 6 }

hpnicfSysReloadRowStatus OBJECT-TYPE
    SYNTAX RowStatus
    MAX-ACCESS read-create
    STATUS current
    DESCRIPTION
        "
        If one of the value of hpnicfSysReloadEntity,hpnicfSysReloadImage
        is invalid, the value of hpnicfSysReloadRowStatus can not be set to the value
        of ACTIVE.

        A valid entry means the specified element is available in current system.
        "
    ::= { hpnicfSysReloadScheduleEntry 7 }

hpnicfSysReloadScheduleTagList OBJECT-TYPE
    SYNTAX SnmpTagList
    MAX-ACCESS read-create
    STATUS current
    DESCRIPTION
    "
    It specifies a tag list for the entry.
    "
    ::= { hpnicfSysReloadScheduleEntry 8 }

hpnicfSysReloadTag OBJECT-TYPE
    SYNTAX SnmpTagValue
    MAX-ACCESS read-write
    STATUS current
    DESCRIPTION
        "This object contains a single tag value which is used
        to select entries in the hpnicfSysReloadScheduleTable.

        In the hpnicfSysReloadScheduleTable,any entry that contains
        a tag value which is equal to the value of this object is
        selected.

        For example, the value of hpnicfSysReloadTag is 'TOM',and the
        hpnicfSysReloadScheduleTagList of each hpnicfSysReloadScheduleTable
        entry are as follows:
        1)'TOM,ROBERT,MARY'
        2)'TOM,DAVE'
        3)'DAVE,MARY'
        Since there are 'TOM' in 1) and 2),so 1) and 2) are selected.


        If this object contains a value of zero length, no entries
        are selected.
        "
    ::= { hpnicfSysReload 4 }
-- End define reload group
hpnicfSysImage OBJECT IDENTIFIER ::= { hpnicfSystemManMIBObjects 4 }

hpnicfSysImageNum OBJECT-TYPE
    SYNTAX Integer32 (0..2147483647)
    MAX-ACCESS read-only
    STATUS current
    DESCRIPTION
        "
        The number of system images. It indicates the
        total entries of hpnicfSysImageTable.
        "
    ::= { hpnicfSysImage 1 }

hpnicfSysImageTable OBJECT-TYPE
    SYNTAX SEQUENCE OF HpnicfSysImageEntry
    MAX-ACCESS not-accessible
    STATUS current
    DESCRIPTION
        "The system image management table.


        When 'copy srcfile destfile' is executed via the CLI, if destfile is not existed,
        then hpnicfSysImageType of the new file will be 'none'; otherwise hpnicfSysImageType keeps its current value.
        When 'move srcfile destfile' is executed via the CLI, hpnicfSysImageType and hpnicfSysImageIndex
         remain the same while hpnicfSysImageLocation changes.
        When 'rename srcfile' is executed via the CLI,hpnicfSysImageType and hpnicfSysImageIndex remain the same
        while hpnicfSysImageName changes.
        When 'delete srcfile' is executed via the CLI, the file is deleted from hpnicfSysImageTable
        while index of the file keeps and will not be allocated.
        "
    ::= { hpnicfSysImage 2 }

hpnicfSysImageEntry OBJECT-TYPE
    SYNTAX HpnicfSysImageEntry
    MAX-ACCESS not-accessible
    STATUS current
    DESCRIPTION
        "
        An entity image entry. Each entry consists of information of an entity image.
        The hpnicfSysImageIndex exclusively defines an image file.
        "
    INDEX { hpnicfSysImageIndex }
    ::= { hpnicfSysImageTable 1 }

HpnicfSysImageEntry ::=
    SEQUENCE {
        hpnicfSysImageIndex            Integer32,
        hpnicfSysImageName             DisplayString,
        hpnicfSysImageSize             Integer32,
        hpnicfSysImageLocation         DisplayString,
        hpnicfSysImageType             INTEGER
     }

hpnicfSysImageIndex OBJECT-TYPE
    SYNTAX Integer32 (0..2147483647)
    MAX-ACCESS not-accessible
    STATUS current
    DESCRIPTION
        "There are two parts for the index depicted as follows:

        31                15             0
        +++++++++++++++++++++++++++++++++++
        + physical index   +  image index +
        +++++++++++++++++++++++++++++++++++

        From bit0 to bit15 (two bytes) is the image index;Image file Index
        is a monotonically increasing integer for the sole purpose of indexing
        events.  When it reaches the maximum value, an extremely unlikely event,
        the agent wraps the value back to 1 and may flush existing entries.

        From bit16 to bit31 (two bytes) is the physical index the same as the
        entPhysicalIndex specified in ENTITY-MIB.
        If ENTITY-MIB is not supported,the value for this object is the unit ID for XRN
        devices ,0 for non-XRN device which has only one main board,the board number for
        non-XRN device which have several main boards.


        Any index beyond the above range will not be supported.

        If a file is added in, its hpnicfSysImageIndex will be the maximum image index plus one.
                        If the image file is removed, renamed, or moved from one place to another,
                        its hpnicfSysImageIndex is not reallocated.
                        If the image file's content is replaced, its hpnicfSysImageIndex will not change.

        "
    ::= { hpnicfSysImageEntry 1 }

hpnicfSysImageName OBJECT-TYPE
    SYNTAX DisplayString (SIZE (0..255))
    MAX-ACCESS read-only
    STATUS current
    DESCRIPTION
        "The file name of the image. It MUST NOT contain the path of the file."
    ::= { hpnicfSysImageEntry 2 }

hpnicfSysImageSize OBJECT-TYPE
    SYNTAX Integer32 (1..2147483647)
    MAX-ACCESS read-only
    STATUS current
    DESCRIPTION
        "
        Size of the file in bytes.
        "
    ::= { hpnicfSysImageEntry 3 }

hpnicfSysImageLocation OBJECT-TYPE
    SYNTAX DisplayString (SIZE (0..255))
    MAX-ACCESS read-only
    STATUS current
    DESCRIPTION
        "
        The directory path of the image.
        Its form should be the same as what defined in file system.
        Currently it is defined as follows:
        For mainboard:   flash:/
        For slave mainboard and subboards: slotN#flash:/
        For XRN devices: unitN>slotN#flash:/
        "
    ::= { hpnicfSysImageEntry 4 }

hpnicfSysImageType OBJECT-TYPE
    SYNTAX INTEGER
        {
        main(1),
        backup(2),
        none(3),
        secure(4),
        main-backup(5),
        main-secure(6),
        backup-secure(7),
        main-backup-secure(8)
        }
    MAX-ACCESS read-write
    STATUS current
    DESCRIPTION
        "
        It indicates the reloading sequence attribute of the image.

        For devices which support dual image:

        If the value is 'main(1)',the image will be the first image
        in the next reloading procedure. If the value is 'backup(2)',
        the image will be used if the main image fails. If the value
        is 'secure(4)', the image will be used if the main image and
        backup image both fail. If the value is 'none(3)',the image will
        not be used in the next reloading procedure.

        At the same time,you also can specify the main image by
        hpnicfSysReloadImage in hpnicfSysReloadScheduleTable. If the
        image is different from previous main image, the previous main image
        will not be main image again. And the image table will update with
        this variation. Vice versa, if you have defined the reload schedule,
        and then you define a new main image through hpnicfSysImageType when you
        are waiting the reload schedule to be executed, the real main image
        will be the latest one.


        It is strongly suggested to define the main image here, not by hpnicfSysReloadImage
        in hpnicfSysReloadScheduleTable.

        There are some rules for setting the value of hpnicfSysImageType:

        a)When a new image file is defined as 'main' or 'backup' file,the hpnicfSysImageType
          of old 'main' or 'backup' file will automatically be 'none'.
        b)It is forbidden to set 'none' attribute manually.
        c)It is forbidden to set 'secure' attribute manually.
        d)If 'main' image is set to 'backup', the file keeps 'main'. And vice versa.
          At this time, the file has 'main-backup' property.
        e)If the secure image is set to 'main' or 'backup', the file has 'main-secure' or 'backup-secure'property.
        f)If the secure image is set to 'main' and 'backup', the file has the 'main-backup-secure' property.
        g)If the none image is set to 'main' or 'backup', the file has the 'main' or 'backup' property.

        The following table describes whether it is ok to set to another state
        directly from original state.

                        +--------------+-----------+-------------+-------------+
                        |   set to     | set to    |  set to     |   set to    |
                        |              |           |             |             |
             original   |    'main'    | 'backup'  |  'none'     |  'secure'   |
             state      |              |           |             |             |
          --------------+--------------+-----------+-------------+-------------+
                        |              |           |             |             |
             main       |     ---      |   yes     |   no        |   no        |
                        |              |           |             |             |
                        |              |           |             |             |
          --------------+--------------+-----------+-------------|-------------+
                        |              |           |             |             |
             backup     |     yes      |   ---     |   no        |   no        |
                        |              |           |             |             |
          --------------+--------------+-----------+-------------|-------------+
                        |              |           |             |             |
                        |              |           |             |             |
              none      |     yes      |   yes     |   ---       |   no        |
                        |              |           |             |             |
          --------------+--------------+-----------+-------------+-------------+
                        |              |           |             |             |
              secure    |     yes      |   yes     |   no        |   ---       |
                        |              |           |             |             |
                        |              |           |             |             |
          --------------+--------------+-----------+-------------+-------------+

        If there is one main image in the system, one row of HpnicfSysReloadScheduleEntry
        whose  hpnicfSysReloadImage is equal to the main image's hpnicfSysImageIndex will be
        created automatically. But if any row is deleted, it will not be created
        automatically in hpnicfSysReloadScheduleTable.




        For the device which doesn't support dual image(main/backup):

        Only 'main' and 'none' is supported and it only can be set from none to main.
        When a new image file is defined as 'main' file,the hpnicfSysImageType of old 'main'
        file will automatically be 'none'.
        "
    ::= { hpnicfSysImageEntry 5 }

-- End define sysImage group

hpnicfSysCFGFile OBJECT IDENTIFIER ::= { hpnicfSystemManMIBObjects 5 }

hpnicfSysCFGFileNum OBJECT-TYPE
    SYNTAX Integer32 (0..2147483647)
    MAX-ACCESS read-only
    STATUS current
    DESCRIPTION
        "
        The number of the configuration files in the system. It indicates the
        total entries of hpnicfSysCFGFileTable.
        "
    ::= { hpnicfSysCFGFile 1 }

hpnicfSysCFGFileTable OBJECT-TYPE
    SYNTAX SEQUENCE OF HpnicfSysCFGFileEntry
    MAX-ACCESS not-accessible
    STATUS current
    DESCRIPTION
        "A table of configuration files in this system.
         At present, the system doesn't support dual configure file,
         it should act as 'dual image' if dual configure file is
         supported.
        "
    ::= { hpnicfSysCFGFile 2 }

hpnicfSysCFGFileEntry OBJECT-TYPE
    SYNTAX HpnicfSysCFGFileEntry
    MAX-ACCESS not-accessible
    STATUS current
    DESCRIPTION
        "
        A configuration file entry. Each entry consists of information of
        a configuration file.
        hpnicfSysCFGFileIndex exclusively decides a configuration file.
        "
    INDEX { hpnicfSysCFGFileIndex }
    ::= { hpnicfSysCFGFileTable 1 }

HpnicfSysCFGFileEntry ::=
    SEQUENCE {
        hpnicfSysCFGFileIndex          Integer32,
        hpnicfSysCFGFileName           DisplayString,
        hpnicfSysCFGFileSize           Integer32,
        hpnicfSysCFGFileLocation       DisplayString
     }

hpnicfSysCFGFileIndex OBJECT-TYPE
    SYNTAX Integer32 (0..2147483647)
    MAX-ACCESS not-accessible
    STATUS current
    DESCRIPTION
       "There are two parts for the index depicted as follows:

        31                15             0
        +++++++++++++++++++++++++++++++++++
        + physical index  + cfgFile index +
        +++++++++++++++++++++++++++++++++++

        From bit0 to bit15 (two bytes) is the configuration file index; the
        configuration file index is a monotonically increasing integer for
        the sole purpose of indexing events. When it reaches the maximum
        value, an extremely unlikely event, the agent wraps the value back
        to 1 and may flush existing entries.

        From bit16 to bit31 (two bytes) is the physical index the same
        as the entPhysicalIndex specified in ENTITY-MIB.
        If ENTITY-MIB is not supported, the value for this object is the unit ID for XRN
        devices ,0 for non-XRN device which has only one slot,the board number for
        non-XRN device which have several slots.

        Any index beyond the above range will not be supported.
        "
    ::= { hpnicfSysCFGFileEntry 1 }

hpnicfSysCFGFileName OBJECT-TYPE
    SYNTAX DisplayString (SIZE (0..255))
    MAX-ACCESS read-only
    STATUS current
    DESCRIPTION
        "
        Configuration file name. The name should not include the colon (:)
        character as it is a special separator character used
        to delineate the device name, partition name and the
        file name.
        "
    ::= { hpnicfSysCFGFileEntry 2 }

hpnicfSysCFGFileSize OBJECT-TYPE
    SYNTAX Integer32 (1..2147483647)
    MAX-ACCESS read-only
    STATUS current
    DESCRIPTION
        "
        Size of the file in bytes. Note that it does
        not include the size of the filesystem file header.
        File size will always be non-zero.
        "
    ::= { hpnicfSysCFGFileEntry 3 }

hpnicfSysCFGFileLocation OBJECT-TYPE
    SYNTAX DisplayString (SIZE (0..255))
    MAX-ACCESS read-only
    STATUS current
    DESCRIPTION
        "
        The directory path of the image.
        Its form should be the same as what defined in filesystem.
        Currently it is defined as follows:
        For mainboard:   flash:/
        For slave mainboard and subboards: slotN#flash:/
        For XRN devices: unitN>slotN#flash:/
        "
    ::= { hpnicfSysCFGFileEntry 4 }
-- End define CFGFile group

-- Begin define bootrom group
hpnicfSysBtmFile OBJECT IDENTIFIER ::= { hpnicfSystemManMIBObjects 6 }

hpnicfSysBtmFileLoad OBJECT IDENTIFIER ::= { hpnicfSysBtmFile 1 }

hpnicfSysBtmLoadMaxNumber OBJECT-TYPE
    SYNTAX Integer32
    MAX-ACCESS read-only
    STATUS current
    DESCRIPTION
        "
        This object shows the maximum number of hpnicfSysBtmLoadEntry in
        each device/unit.
        "
    ::= { hpnicfSysBtmFileLoad 1 }

hpnicfSysBtmLoadTable OBJECT-TYPE
    SYNTAX SEQUENCE OF HpnicfSysBtmLoadEntry
    MAX-ACCESS not-accessible
    STATUS current
    DESCRIPTION
        "
        This table is used to update the bootrom and show the results of
        the update operation.
        The bootrom files are listed at the hpnicfFlhFileTable.  These files
        are used to update bootrom.
        "
    ::= { hpnicfSysBtmFile 2 }

hpnicfSysBtmLoadEntry OBJECT-TYPE
    SYNTAX HpnicfSysBtmLoadEntry
    MAX-ACCESS not-accessible
    STATUS current
    DESCRIPTION
        "
        Entries in the hpnicfSysBtmLoadTable are created and deleted using
        the hpnicfSysBtmRowStatus object.

        When a new row is being created and the number of entries is
        hpnicfSysBtmLoadMaxNumber, the row with minimal value of
        hpnicfSysBtmLoadTime and the value of hpnicfSysBtmFileType is none(2),
        should be destroyed automatically.
        "
    INDEX { hpnicfSysBtmLoadIndex }
    ::= { hpnicfSysBtmLoadTable 1 }

HpnicfSysBtmLoadEntry ::=
    SEQUENCE {
        hpnicfSysBtmLoadIndex          Integer32,
        hpnicfSysBtmFileName           OCTET STRING,
        hpnicfSysBtmFileType           INTEGER,
        hpnicfSysBtmRowStatus          RowStatus,
        hpnicfSysBtmErrorStatus        INTEGER,
        hpnicfSysBtmLoadTime           TimeTicks
     }

hpnicfSysBtmLoadIndex OBJECT-TYPE
    SYNTAX Integer32 (1..2147483647)
    MAX-ACCESS not-accessible
    STATUS current
    DESCRIPTION
        "
        The index of hpnicfSysBtmLoadTable. There are two parts for this
        index depicted as follows:

        31                  15                  0
        +++++++++++++++++++++++++++++++++++++++++
        + physical index     +     random index +
        ( bit 16..31 )              ( bit 0..15 )
        +++++++++++++++++++++++++++++++++++++++++

        From bit0 to bit15 (two bytes), if the row is created by command
        line, the value is determined by system, and if the row is created
        by SNMP, the value is determined by users.

        From bit16 to bit31 (two bytes) is the physical index the same as
        the entPhysicalIndex specified in ENTITY-MIB.

        If ENTITY-MIB is not supported, the value of this object is the
        unit ID for XRN devices, 0 for non-XRN device which has only one
        main board, the board number for non-XRN device which has multiple
        main boards.
       "
    ::= { hpnicfSysBtmLoadEntry 1 }

hpnicfSysBtmFileName OBJECT-TYPE
    SYNTAX OCTET STRING(SIZE (1..64))
    MAX-ACCESS read-create
    STATUS current
    DESCRIPTION
        "
        The bootrom file name is determined by the users.  The file must
        exist in corresponding entity.

        The validity of the bootrom file will be identified by system.
        If the file is invalid, the bootrom should fail to be updated,
        and the value of hpnicfSysBtmErrorStatus should be failed(4).
        "
    ::= { hpnicfSysBtmLoadEntry 2 }

hpnicfSysBtmFileType OBJECT-TYPE
    SYNTAX INTEGER
       {
       main(1),
       none(2)
       }
    MAX-ACCESS read-create
    STATUS current
    DESCRIPTION
        "
        main(1) - The effective bootrom file.
        none(2) - The noneffective file.

        When bootrom is being updated, this object must be set to main(1).

        When bootrom is updated successfully, this object should be
        main(1), and the former object with the same physical index should
        be none(2).

        When bootrom failed to be updated, this object should be none(2).
        "
    ::= { hpnicfSysBtmLoadEntry 3 }

hpnicfSysBtmRowStatus OBJECT-TYPE
    SYNTAX RowStatus
    MAX-ACCESS read-create
    STATUS current
    DESCRIPTION
        "
        Only support active(1), createAndGo(4), destroy(6).  When a row
        is created successfully, the value of this object should be active(1),
        the value of hpnicfSysBtmFileName and hpnicfSysBtmFileType can not be
        modified by users.

        When bootrom is being updated, the value of hpnicfSysBtmErrorStatus
        is inProgress(2).

        When bootrom failed to be updated, the value of hpnicfSysBtmErrorStatus
        should be failed(4).

        When bootrom is updated successfully, the value of hpnicfSysBtmErrorStatus
        should be success(3).  The value of hpnicfSysCurUpdateBtmFileName
        should change to the new bootrom file name.

        When another row is created successfully with the same physical
        index, and the update is successful, then the value of former
        hpnicfSysBtmFileType should be none(2) automatically.

        If a row is destroyed, hpnicfSysCurUpdateBtmFileName should not change.

        If a device/unit reboots, hpnicfSysBtmLoadTable should be empty.
        "
    ::= { hpnicfSysBtmLoadEntry 4 }

hpnicfSysBtmErrorStatus OBJECT-TYPE
    SYNTAX INTEGER
       {
       invalidFile(1),
       inProgress(2),
       success(3),
       failed(4)
       }
    MAX-ACCESS read-only
    STATUS current
    DESCRIPTION
        "
        This object shows the status of the specified operation after
        creating a row.
        invalidFile(1) - file is invalid.
        inProgress(2)  - the operation is in progress.
        success(3)     - the operation was done successfully.
        failed(4)      - the operation failed.
        "
    ::= { hpnicfSysBtmLoadEntry 5 }

hpnicfSysBtmLoadTime OBJECT-TYPE
    SYNTAX TimeTicks
    MAX-ACCESS read-only
    STATUS current
    DESCRIPTION
        "
        This object indicates operation time.
        "
    ::= { hpnicfSysBtmLoadEntry 6 }

-- End define Bootrom group

hpnicfSysPackage OBJECT IDENTIFIER ::= { hpnicfSystemManMIBObjects 7 }

hpnicfSysPackageNum OBJECT-TYPE
    SYNTAX Integer32 (0..2147483647)
    MAX-ACCESS read-only
    STATUS current
    DESCRIPTION
        "
        The number of software packages.  It indicates the
        total entries of hpnicfSysPackageTable.
        "
    ::= { hpnicfSysPackage 1 }

hpnicfSysPackageTable OBJECT-TYPE
    SYNTAX SEQUENCE OF HpnicfSysPackageEntry
    MAX-ACCESS not-accessible
    STATUS current
    DESCRIPTION
        "The system package management table.
        "
    ::= { hpnicfSysPackage 2 }

hpnicfSysPackageEntry OBJECT-TYPE
    SYNTAX HpnicfSysPackageEntry
    MAX-ACCESS not-accessible
    STATUS current
    DESCRIPTION
        "
        An software package entry.  Each entry consists of information of
        an software package.
        "
    INDEX { hpnicfSysPackageIndex }
    ::= { hpnicfSysPackageTable 1 }

HpnicfSysPackageEntry ::=
    SEQUENCE {
        hpnicfSysPackageIndex            Integer32,
        hpnicfSysPackageName             DisplayString,
        hpnicfSysPackageSize             Unsigned32,
        hpnicfSysPackageLocation         DisplayString,
        hpnicfSysPackageType             INTEGER,
        hpnicfSysPackageAttribute        INTEGER,
        hpnicfSysPackageStatus           INTEGER,
        hpnicfSysPackageDescription      DisplayString,
        hpnicfSysPackageFeature          DisplayString,
        hpnicfSysPackageVersion          DisplayString,
        hpnicfSysPackageLoadAttribute    INTEGER,
        hpnicfSysPackageModel            DisplayString
    }

hpnicfSysPackageIndex OBJECT-TYPE
    SYNTAX Integer32 (1..2147483647)
    MAX-ACCESS not-accessible
    STATUS current
    DESCRIPTION
        "There are two parts for the index depicted as follows:

        31                15             0
        +++++++++++++++++++++++++++++++++++
        + physical index   +  package index +
        +++++++++++++++++++++++++++++++++++

        From bit0 to bit15 (two bytes) is the Package index; Package file Index
        is a monotonically increasing integer for the sole purpose of indexing
        events.  When it reaches the maximum value, an extremely unlikely
        event, the agent wraps the value back to 1 and may flush existing
        entries.

        From bit16 to bit31 (two bytes) is the physical index the same as the
        entPhysicalIndex specified in ENTITY-MIB.

        Any index beyond the above range will not be supported.

        If a file is added in, its hpnicfSysPackageIndex will be the maximum
        image index plus one.
        If the package file is removed, renamed, or moved from one place to
        another, its hpnicfSysPackageIndex is not reallocated.
        If the package file's content is replaced, its hpnicfSysPackageIndex will
        not change.
        "
    ::= { hpnicfSysPackageEntry 1 }

hpnicfSysPackageName OBJECT-TYPE
    SYNTAX DisplayString (SIZE (0..255))
    MAX-ACCESS read-only
    STATUS current
    DESCRIPTION
        "
        The file name of the package.  It MUST NOT contain the path
        of the file.
        "
    ::= { hpnicfSysPackageEntry 2 }

hpnicfSysPackageSize OBJECT-TYPE
    SYNTAX Unsigned32 (1..4294967295)
    MAX-ACCESS read-only
    STATUS current
    DESCRIPTION
        "
        Size of the file in bytes.
        "
    ::= { hpnicfSysPackageEntry 3 }

hpnicfSysPackageLocation OBJECT-TYPE
    SYNTAX DisplayString (SIZE (0..255))
    MAX-ACCESS read-only
    STATUS current
    DESCRIPTION
        "
        The directory path of the package.
        Its form should be the same as what defined in file system.
        Currently it is defined as follows:
        For mainboard:   flash:/
        For slave mainboard and subboards: slotN#flash:/
        "
    ::= { hpnicfSysPackageEntry 4 }

hpnicfSysPackageType OBJECT-TYPE
    SYNTAX INTEGER
        {
        boot(1),
        system(2),
        feature(3),
        patch(4)
        }
    MAX-ACCESS read-only
    STATUS current
    DESCRIPTION
        "
        It indicates the type of the package file.
        boot    :  kernel, file system, memory management and other
                   core components.
        system  :  interface management, configuration management and other
                   basic system package.
        feature :  feature packages, providing different services.
        patch   :  patch file contains fixes for a specific defect.
        "
    ::= { hpnicfSysPackageEntry 5 }

hpnicfSysPackageAttribute OBJECT-TYPE
    SYNTAX INTEGER
        {
        none(1),
        primary(2),
        secondary(3),
        primarySecondary(4)
        }
    MAX-ACCESS read-write
    STATUS current
    DESCRIPTION
        "
        It indicates the attribute of the package file.
        If the value is 'primary', the package will be the first package
        in the next reloading procedure.  If the value is 'secondary',
        the package will be used if the primary package fails.
        If the value is 'none', it will not be used in the next reloading
        procedure.
        "
    ::= { hpnicfSysPackageEntry 6 }

hpnicfSysPackageStatus OBJECT-TYPE
    SYNTAX INTEGER
        {
        active(1),
        inactive(2)
        }
    MAX-ACCESS read-only
    STATUS current
    DESCRIPTION
    "
    It indicates the status of the package file.  If this file is used in the
    current system, its status is 'active'.
    "
    ::= { hpnicfSysPackageEntry 7 }

hpnicfSysPackageDescription OBJECT-TYPE
    SYNTAX DisplayString (SIZE (0..255))
    MAX-ACCESS read-only
    STATUS current
    DESCRIPTION
    "
    It is the description of the package.
    "
    ::= { hpnicfSysPackageEntry 8 }

hpnicfSysPackageFeature OBJECT-TYPE
    SYNTAX DisplayString (SIZE (0..255))
    MAX-ACCESS read-only
    STATUS current
    DESCRIPTION
    "
    Indicate the feature of the package.  Different package files
    could be the same feature.
    "
    ::= { hpnicfSysPackageEntry 9 }

hpnicfSysPackageVersion OBJECT-TYPE
    SYNTAX DisplayString (SIZE (0..255))
    MAX-ACCESS read-only
    STATUS current
    DESCRIPTION
    "
    Indicate the version of the package.
    "
    ::= { hpnicfSysPackageEntry 10 }

hpnicfSysPackageLoadAttribute OBJECT-TYPE
    SYNTAX INTEGER
    {
        none(1),
        primary(2),
        secondary(3),
        primarySecondary(4)
    }
    MAX-ACCESS read-write
    STATUS current
    DESCRIPTION
    "File attribute of the startup image for an extended device to load from
    the parent device.  Examples of extended devices include PEXs and firewall
    modules.  The none attribute is returned if the image is not for extended
    devices, or if the load attribute is not specified."
    ::= { hpnicfSysPackageEntry 11 }

hpnicfSysPackageModel OBJECT-TYPE
    SYNTAX DisplayString (SIZE (0..63))
    MAX-ACCESS read-only
    STATUS current
    DESCRIPTION
    "Indicates whether the image file is for an extended device or the parent
    device.  Examples of extended devices include PEXs and firewall modules."
    ::= { hpnicfSysPackageEntry 12 }

-- begin package operate table
hpnicfSysPackageOperateEntryLimit OBJECT-TYPE
    SYNTAX Integer32 (0..2147483647)
    MAX-ACCESS read-write
    STATUS current
    DESCRIPTION
        "
        The maximum number of the entries in hpnicfSysPackageOperateTable.
        "
    ::= { hpnicfSysPackage 3 }

hpnicfSysPackageOperateTable OBJECT-TYPE
    SYNTAX SEQUENCE OF HpnicfSysPackageOperateEntry
    MAX-ACCESS not-accessible
    STATUS current
    DESCRIPTION
        "A table of package file operate."
   ::= { hpnicfSysPackage 4 }

hpnicfSysPackageOperateEntry OBJECT-TYPE
    SYNTAX HpnicfSysPackageOperateEntry
    MAX-ACCESS not-accessible
    STATUS current
    DESCRIPTION
        "
        An operate request entry.
        "
    INDEX { hpnicfSysPackageOperateIndex }
    ::= { hpnicfSysPackageOperateTable 1 }

HpnicfSysPackageOperateEntry ::=
    SEQUENCE {
        hpnicfSysPackageOperateIndex                   Integer32,
        hpnicfSysPackageOperatePackIndex               Integer32,
        hpnicfSysPackageOperateStatus                  INTEGER,
        hpnicfSysPackageOperateRowStatus               RowStatus,
        hpnicfSysPackageOperateResult                  INTEGER
     }

hpnicfSysPackageOperateIndex OBJECT-TYPE
    SYNTAX Integer32 (1..2147483647)
    MAX-ACCESS not-accessible
    STATUS current
    DESCRIPTION
        "
        The unique index value of a row in this table.
        "
    ::= { hpnicfSysPackageOperateEntry 1 }

hpnicfSysPackageOperatePackIndex OBJECT-TYPE
    SYNTAX Integer32 (1..2147483647)
    MAX-ACCESS   read-create
    STATUS current
    DESCRIPTION
        "
        Specify the package file in the hpnicfSysPackageTable.
        "
    ::= { hpnicfSysPackageOperateEntry 2 }

hpnicfSysPackageOperateStatus OBJECT-TYPE
    SYNTAX INTEGER
        {
        active(1),
        inactive(2)
        }
    MAX-ACCESS read-create
    STATUS current
    DESCRIPTION
        "
        activate or deactivate a package in the hpnicfSysPackageTable.
        "
    ::= { hpnicfSysPackageOperateEntry 3 }

hpnicfSysPackageOperateRowStatus OBJECT-TYPE
    SYNTAX  RowStatus
    MAX-ACCESS read-create
    STATUS current
    DESCRIPTION
        "
        the status of this table entry.
        When the status is active all the
        object's value in the entry is not
        allowed to modified.
        "
    ::= { hpnicfSysPackageOperateEntry 4 }

hpnicfSysPackageOperateResult OBJECT-TYPE
    SYNTAX  INTEGER
      {
        opInProgress(1),
        opSuccess(2),
        opUnknownFailure(3),
        opInvalidFile(4),
        opNotSupport(5)
      }
    MAX-ACCESS read-only
    STATUS current
    DESCRIPTION
        "
        the result of the operation.
        "
    ::= { hpnicfSysPackageOperateEntry 5 }
-- End define sysPackage group

-- Begin define sysIpe group
hpnicfSysIpeFile OBJECT IDENTIFIER ::= { hpnicfSystemManMIBObjects 8 }

hpnicfSysIpeFileNum OBJECT-TYPE
    SYNTAX Integer32 (0..2147483647)
    MAX-ACCESS read-only
    STATUS current
    DESCRIPTION
        "
        The number of software IPE(Image Package Envelop) files.
        It indicates the total entries of hpnicfSysIpeFileTable.
        "
    ::= { hpnicfSysIpeFile 1 }

hpnicfSysIpeFileTable OBJECT-TYPE
    SYNTAX SEQUENCE OF HpnicfSysIpeFileEntry
    MAX-ACCESS not-accessible
    STATUS current
    DESCRIPTION
        "The system IPE file manage table.
        "
    ::= { hpnicfSysIpeFile 2 }

hpnicfSysIpeFileEntry OBJECT-TYPE
    SYNTAX HpnicfSysIpeFileEntry
    MAX-ACCESS not-accessible
    STATUS current
    DESCRIPTION
        "
        An IPE package file entry.  Each entry consists of information of
        an IPE package file.
        hpnicfSysIpeFileIndex exclusively decides an IPE file.
        "
    INDEX { hpnicfSysIpeFileIndex }
    ::= { hpnicfSysIpeFileTable 1 }

HpnicfSysIpeFileEntry ::=
    SEQUENCE {
        hpnicfSysIpeFileIndex            Integer32,
        hpnicfSysIpeFileName             DisplayString,
        hpnicfSysIpeFileSize             Unsigned32,
        hpnicfSysIpeFileLocation         DisplayString,
        hpnicfSysIpeFileModel            SnmpTagList
     }

hpnicfSysIpeFileIndex OBJECT-TYPE
    SYNTAX Integer32 (1..2147483647)
    MAX-ACCESS not-accessible
    STATUS current
    DESCRIPTION
        "There are two parts for the index depicted as follows:

        31                15             0
        +++++++++++++++++++++++++++++++++++
        + physical index   +  IPE   index +
        +++++++++++++++++++++++++++++++++++

        From bit0 to bit15 (two bytes) is the IPE file index; IPE file Index
        is a monotonically increasing integer for the sole purpose of indexing
        events.  When it reaches the maximum value, an extremely unlikely
        event, the agent wraps the value back to 1 and may flush existing
        entries.

        From bit16 to bit31 (two bytes) is the physical index the same as the
        entPhysicalIndex specified in ENTITY-MIB.

        Any index beyond the above range will not be supported.

        If a file is added in, its hpnicfSysIpeFileIndex will be the maximum image
        ndex plus one.
        If the IPE file is removed, renamed, or moved from one place to
        another, its hpnicfSysIpeFileIndex is not reallocated.
        If the IPE file's content is replaced, its hpnicfSysIpeFileIndex will not
        change.
        "
    ::= { hpnicfSysIpeFileEntry 1 }

hpnicfSysIpeFileName OBJECT-TYPE
    SYNTAX DisplayString (SIZE (0..255))
    MAX-ACCESS read-only
    STATUS current
    DESCRIPTION
        "
        The file name of the IPE file.  It MUST NOT contain the path of
        the file.
        "
    ::= { hpnicfSysIpeFileEntry 2 }

hpnicfSysIpeFileSize OBJECT-TYPE
    SYNTAX Unsigned32 (1..4294967295)
    MAX-ACCESS read-only
    STATUS current
    DESCRIPTION
        "
        Size of the file in bytes.
        "
    ::= { hpnicfSysIpeFileEntry 3 }

hpnicfSysIpeFileLocation OBJECT-TYPE
    SYNTAX DisplayString (SIZE (0..255))
    MAX-ACCESS read-only
    STATUS current
    DESCRIPTION
        "
        The directory path of the IPE file.
        Its form should be the same as what defined in file system.
        Currently it is defined as follows:
        For mainboard:   flash:/
        For slave mainboard and subboards: slotN#flash:/
        "
    ::= { hpnicfSysIpeFileEntry 4 }

hpnicfSysIpeFileModel OBJECT-TYPE
    SYNTAX SnmpTagList
    MAX-ACCESS read-only
    STATUS current
    DESCRIPTION
        "Device models for which the IPE file contains software images.  For
        the ease of software upgrade, an IPE file might contain software images
        for a parent device and extended devices.  Examples of extended devices
        include PEXs and firewall modules."
    ::= { hpnicfSysIpeFileEntry 5 }

-- Begin define Ipe-package
hpnicfSysIpePackageTable OBJECT-TYPE
    SYNTAX SEQUENCE OF HpnicfSysIpePackageEntry
    MAX-ACCESS not-accessible
    STATUS current
    DESCRIPTION
        "
        The IPE package file table.  It shows the package files in
        the IPE file.
        "
    ::= { hpnicfSysIpeFile 3 }

hpnicfSysIpePackageEntry OBJECT-TYPE
    SYNTAX HpnicfSysIpePackageEntry
    MAX-ACCESS not-accessible
    STATUS current
    DESCRIPTION
        "
        An entry of the hpnicfIpePackageTable.  Indexed by
        hpnicfSysIpeFileIndex and hpnicfSysIpePackageIndex.
        "
    INDEX { hpnicfSysIpeFileIndex, hpnicfSysIpePackageIndex }
    ::= { hpnicfSysIpePackageTable 1 }

HpnicfSysIpePackageEntry ::=
    SEQUENCE {
        hpnicfSysIpePackageIndex            Integer32,
        hpnicfSysIpePackageName             DisplayString,
        hpnicfSysIpePackageSize             Unsigned32,
        hpnicfSysIpePackageType             INTEGER,
        hpnicfSysIpePackageDescription      DisplayString,
        hpnicfSysIpePackageFeature          DisplayString,
        hpnicfSysIpePackageVersion          DisplayString,
        hpnicfSysIpePackageModel            DisplayString
     }

hpnicfSysIpePackageIndex OBJECT-TYPE
    SYNTAX Integer32 (1..2147483647)
    MAX-ACCESS not-accessible
    STATUS current
    DESCRIPTION
        "
        It is the IPE package index; IPE Package Index
        is a monotonically increasing integer for the sole purpose of indexing
        events.  When it reaches the maximum value, an extremely unlikely
        event, the agent wraps the value back to 1 and may flush existing
        entries.

        Any index beyond the above range will not be supported.
        "
    ::= { hpnicfSysIpePackageEntry 1 }

hpnicfSysIpePackageName OBJECT-TYPE
    SYNTAX DisplayString (SIZE (0..255))
    MAX-ACCESS read-only
    STATUS current
    DESCRIPTION
        "The file name of the package file."
    ::= { hpnicfSysIpePackageEntry 2 }

hpnicfSysIpePackageSize OBJECT-TYPE
    SYNTAX Unsigned32 (1..4294967295)
    MAX-ACCESS read-only
    STATUS current
    DESCRIPTION
        "
        Size of the package file in bytes.
        "
    ::= { hpnicfSysIpePackageEntry 3 }

hpnicfSysIpePackageType OBJECT-TYPE
    SYNTAX INTEGER
        {
        boot(1),
        system(2),
        feature(3),
        patch(4)
        }
    MAX-ACCESS read-only
    STATUS current
    DESCRIPTION
        "
        It indicates the type of the package file.
        boot    : kernel, file system, memory management and
                  other core components.
        system  : interface management, configuration management and
                  other basic system package.
        feature : feature packages, providing different services.
        patch   : patch file contains fixes for a specific defect.
        "
    ::= { hpnicfSysIpePackageEntry 4 }

hpnicfSysIpePackageDescription OBJECT-TYPE
    SYNTAX DisplayString (SIZE (0..255))
    MAX-ACCESS read-only
    STATUS current
    DESCRIPTION
    "
    It is the description of the package.
    "
    ::= { hpnicfSysIpePackageEntry 5 }

hpnicfSysIpePackageFeature OBJECT-TYPE
    SYNTAX DisplayString (SIZE (0..255))
    MAX-ACCESS read-only
    STATUS current
    DESCRIPTION
    "
    Indicate the feature of the package.
    "
    ::= { hpnicfSysIpePackageEntry 6 }

hpnicfSysIpePackageVersion OBJECT-TYPE
    SYNTAX DisplayString (SIZE (0..255))
    MAX-ACCESS read-only
    STATUS current
    DESCRIPTION
    "
    The version of the package.
    "
    ::= { hpnicfSysIpePackageEntry 7 }

hpnicfSysIpePackageModel OBJECT-TYPE
    SYNTAX DisplayString (SIZE (0..63))
    MAX-ACCESS read-only
    STATUS current
    DESCRIPTION
    "Indicates whether the image package file is for an extended device, the
    parent device, or both.  Examples of extended devices include PEXs and
    firewall modules."
    ::= { hpnicfSysIpePackageEntry 8 }
-- End define Ipe-package

-- Begin define Ipe File operate table
hpnicfSysIpeFileOperateTable OBJECT-TYPE
    SYNTAX SEQUENCE OF HpnicfSysIpeFileOperateEntry
    MAX-ACCESS not-accessible
    STATUS current
    DESCRIPTION
        "A table of IPE file operate."
   ::= { hpnicfSysIpeFile 4 }

hpnicfSysIpeFileOperateEntry OBJECT-TYPE
    SYNTAX HpnicfSysIpeFileOperateEntry
    MAX-ACCESS not-accessible
    STATUS current
    DESCRIPTION
        "
        An operate request entry.
        "
    INDEX { hpnicfSysIpeFileOperateIndex }
    ::= { hpnicfSysIpeFileOperateTable 1 }

HpnicfSysIpeFileOperateEntry ::=
    SEQUENCE {
        hpnicfSysIpeFileOperateIndex                   Integer32,
        hpnicfSysIpeFileOperateFileIndex               Integer32,
        hpnicfSysIpeFileOperateAttribute               INTEGER,
        hpnicfSysIpeFileOperateRowStatus               RowStatus,
        hpnicfSysIpeFileOperateResult                  INTEGER
     }

hpnicfSysIpeFileOperateIndex OBJECT-TYPE
    SYNTAX Integer32 (1..2147483647)
    MAX-ACCESS not-accessible
    STATUS current
    DESCRIPTION
        "
        The unique index value of a row in this table.
        "
    ::= { hpnicfSysIpeFileOperateEntry 1 }

hpnicfSysIpeFileOperateFileIndex OBJECT-TYPE
    SYNTAX Integer32 (1..2147483647)
    MAX-ACCESS   read-create
    STATUS current
    DESCRIPTION
        "
        Specify the IPE file in the hpnicfSysIpeFileTable.  This IPE file
        will be unpacked to package files.
        "
    ::= { hpnicfSysIpeFileOperateEntry 2 }

hpnicfSysIpeFileOperateAttribute OBJECT-TYPE
    SYNTAX INTEGER
        {
        none(1),
        primary(2),
        secondary(3),
        primarySecondary(4)
        }
    MAX-ACCESS read-create
    STATUS current
    DESCRIPTION
        "
        It indicates the attribute of the IPE file when it is used in the reloading.
        If the value is 'primary', the packages in the IPE file will be the
        first packages in the next reloading procedure.
        If the value is 'secondary', the package in the IPE file will be used
        if the primary packages fails.
        If the value is 'none', the IPE file is only unpacked,
        will not be used in the reloading procedure.
        "
    ::= { hpnicfSysIpeFileOperateEntry 3 }

hpnicfSysIpeFileOperateRowStatus OBJECT-TYPE
    SYNTAX  RowStatus
    MAX-ACCESS read-create
    STATUS current
    DESCRIPTION
        "
        the status of this table entry.
        When the status is active all the
        object's value in the entry is not
        allowed to modified.
        "
    ::= { hpnicfSysIpeFileOperateEntry 4 }

hpnicfSysIpeFileOperateResult OBJECT-TYPE
    SYNTAX  INTEGER
      {
        opInProgress(1),
        opSuccess(2),
        opUnknownFailure(3),
        opInvalidFile(4),
        opDeviceFull(5),
        opFileOpenError(6)
      }
    MAX-ACCESS read-only
    STATUS current
    DESCRIPTION
        "
        the result of the operation.
        "
    ::= { hpnicfSysIpeFileOperateEntry 5 }
-- End define IpePackage operate table

hpnicfSysSetBootImage OBJECT IDENTIFIER ::= { hpnicfSystemManMIBObjects 9 }

hpnicfSysSetBootImageOp OBJECT IDENTIFIER ::= { hpnicfSysSetBootImage 1 }

hpnicfSysSetBootImageAction OBJECT-TYPE
    SYNTAX INTEGER
        {
        none(1),
        done(2),
        bootLoadPrimary(3),
        bootLoadSecondary(4),
        bootLoadPrimarySecondary(5),
        bootPrimary(6),
        bootSecondary(7),
        bootPrimarySecondary(8),
        loadPrimary(9),
        loadSecondary(10),
        loadPrimarySecondary(11)
        }
    MAX-ACCESS read-write
    STATUS current
    DESCRIPTION
        "Sets images as primary startup images, secondary startup images, or
        both.  Primary startup images are also called 'main' startup images.
        For extended devices, startup images saved on their local media are
        called 'local startup images,' and images saved on the parent device
        are called 'remote startup images.'
        none: Returns a success without setting image attributes.
        done: Clears data for the previous startup image operation.  This
        object must be set 'done' before each startup image operation.

        -------------------------+-----------------------+---------------------------------------------------
            Action               |   Parent devices      |                  Extended devices
        -------------------------+-----------------------+---------------------------------------------------
        bootLoadPrimary          | Sets images as the    | Sets images as the primary startup images
                                 | primary startup       |
                                 | images                | With storage medium: Sets both local and
                                 |                       |                      remote startup images
                                 |                       | Without storage medium: Sets remote startup images
        -------------------------+-----------------------+---------------------------------------------------
        bootLoadSecondary        | Sets images as the    | Sets images as the backup startup images
                                 | backup startup images |
                                 |                       | With storage medium: Sets both local and
                                 |                       |                      remote startup images
                                 |                       | Without storage medium: Sets remote startup images
        -------------------------+-----------------------+---------------------------------------------------
        bootLoadPrimarySecondary | Sets images as both   | Sets images as both the primary and backup startup
                                 | the primary and       | images
                                 | backup startup images | With storage medium: Sets both local and
                                 |                       |                      remote startup images
                                 |                       | Without storage medium: Sets remote startup images
        -------------------------+-----------------------+---------------------------------------------------
        bootPrimary              | Sets images as the    | Sets images as the primary startup images
                                 | primary startup       |
                                 | images                | With storage medium: Sets local startup images
                                 |                       | Without storage medium: N/A
        -------------------------+-----------------------+---------------------------------------------------
        bootSecondary            | Sets images as the    | Sets images as the backup startup images
                                 | backup startup images |
                                 |                       | With storage medium: Sets local startup images
                                 |                       | Without storage medium: N/A
        -------------------------+-----------------------+---------------------------------------------------
        bootPrimarySecondary     | Sets images as both   | Sets images as both the primary and backup startup
                                 | the primary and       | images
                                 | backup startup images | With storage medium: Sets local startup images
                                 |                       | Without storage medium: N/A
        -------------------------+-----------------------+---------------------------------------------------
        loadPrimary              | N/A                   | Sets images as the remote primary startup images
        -------------------------+-----------------------+---------------------------------------------------
        loadSecondary            | N/A                   | Sets images as the remote backup startup images
        -------------------------+-----------------------+---------------------------------------------------
        loadPrimarySecondary     | N/A                   | Sets images as both the remote primary and
                                 |                       | backup startup images
        -------------------------+-----------------------+---------------------------------------------------
        "
    ::= { hpnicfSysSetBootImageOp 1 }

hpnicfSysSetBootImageFileOverWrite OBJECT-TYPE
    SYNTAX TruthValue
    MAX-ACCESS read-write
    STATUS current
    DESCRIPTION
        "Determines whether to overwrite the existing image file with the same
        name as the downloaded image file. "
    DEFVAL { false }
    ::= { hpnicfSysSetBootImageOp 2 }

hpnicfSysSetBootImageRemoveIpeFile OBJECT-TYPE
    SYNTAX TruthValue
    MAX-ACCESS read-write
    STATUS current
    DESCRIPTION
        "Determines whether the IPE file will be removed when the startup
        images are set successfully.  If this object is set to TRUE,
        the IPE file will be removed."
    DEFVAL { false }
    ::= { hpnicfSysSetBootImageOp 3 }

hpnicfSysSetBootImageStatus OBJECT-TYPE
    SYNTAX INTEGER
        {
        none(1),
        doing(2),
        success(3),
        failed(4)
        }
    MAX-ACCESS read-only
    STATUS current
    DESCRIPTION
        "Status of the startup image set operation."
    ::= { hpnicfSysSetBootImageOp 4 }

hpnicfSysSetBootImageFailedReason OBJECT-TYPE
    SYNTAX DisplayString (SIZE (0..255))
    MAX-ACCESS read-only
    STATUS current
    DESCRIPTION
        "Startup image operation failure reason.  The field is empty if the
        operation was successful."
    ::= { hpnicfSysSetBootImageOp 5 }

hpnicfSysBootPackageTable OBJECT-TYPE
    SYNTAX SEQUENCE OF HpnicfSysBootPackageEntry
    MAX-ACCESS not-accessible
    STATUS current
    DESCRIPTION
        "Table of images to be set as startup images.  It should be used when
         hpnicfSysBootIpeTable is empty."
    ::= { hpnicfSysSetBootImage 2 }

hpnicfSysBootPackageEntry OBJECT-TYPE
    SYNTAX HpnicfSysBootPackageEntry
    MAX-ACCESS not-accessible
    STATUS current
    DESCRIPTION
        "Entry of the image table."
    INDEX { hpnicfSysBootPackageIndex }
    ::= { hpnicfSysBootPackageTable 1 }

HpnicfSysBootPackageEntry ::=
    SEQUENCE {
        hpnicfSysBootPackageIndex
            Integer32,
        hpnicfSysBootPackageRowStatus
            RowStatus
     }

hpnicfSysBootPackageIndex OBJECT-TYPE
    SYNTAX Integer32 (1..2147483647)
    MAX-ACCESS not-accessible
    STATUS current
    DESCRIPTION
        "Index of the software images.  The index must be included
        in hpnicfSysPackageTable."
    ::= { hpnicfSysBootPackageEntry 1 }

hpnicfSysBootPackageRowStatus OBJECT-TYPE
    SYNTAX RowStatus
    MAX-ACCESS read-create
    STATUS current
    DESCRIPTION
        "Row status of the image entry."
    ::= { hpnicfSysBootPackageEntry 2 }

hpnicfSysBootIpeTable OBJECT-TYPE
    SYNTAX SEQUENCE OF HpnicfSysBootIpeEntry
    MAX-ACCESS not-accessible
    STATUS current
    DESCRIPTION
        "Table of the IPE files to be set for startup.  It should be used when
        hpnicfSysBootPackageTable is empty."
    ::= { hpnicfSysSetBootImage 3 }

hpnicfSysBootIpeEntry OBJECT-TYPE
    SYNTAX HpnicfSysBootIpeEntry
    MAX-ACCESS not-accessible
    STATUS current
    DESCRIPTION
        "Entry in the IPE file table."
    INDEX { hpnicfSysBootIpeIndex }
    ::= { hpnicfSysBootIpeTable 1 }

HpnicfSysBootIpeEntry ::=
    SEQUENCE
        {
        hpnicfSysBootIpeIndex
            Integer32,
        hpnicfSysBootIpeRowStatus
            RowStatus
        }

hpnicfSysBootIpeIndex OBJECT-TYPE
    SYNTAX Integer32 (1..2147483647)
    MAX-ACCESS not-accessible
    STATUS current
    DESCRIPTION
        "IPE file index.  The index must be included in hpnicfSysIpeFileTable."
    ::= { hpnicfSysBootIpeEntry 1 }

hpnicfSysBootIpeRowStatus OBJECT-TYPE
    SYNTAX RowStatus
    MAX-ACCESS read-create
    STATUS current
    DESCRIPTION
        "Row status of the IPE file table entry."
    ::= { hpnicfSysBootIpeEntry 2 }

hpnicfSysSetBootImageResultTable OBJECT-TYPE
    SYNTAX SEQUENCE OF HpnicfSysSetBootImageResultEntry
    MAX-ACCESS not-accessible
    STATUS current
    DESCRIPTION
        "Table of startup image operation results.  This table shows the
        result for each card."
    ::= { hpnicfSysSetBootImage 4 }

hpnicfSysSetBootImageResultEntry OBJECT-TYPE
    SYNTAX HpnicfSysSetBootImageResultEntry
    MAX-ACCESS not-accessible
    STATUS current
    DESCRIPTION
        "Entry in the startup image operation result table."
    INDEX { hpnicfSysSetBootImageResultIndex }
    ::= { hpnicfSysSetBootImageResultTable 1 }

HpnicfSysSetBootImageResultEntry ::=
    SEQUENCE {
        hpnicfSysSetBootImageResultIndex
            Integer32,
        hpnicfSysSetBootImageResultStatusOfEachCard
            INTEGER,
        hpnicfSysSetBootImageFailedReasonOfEachCard
            DisplayString
     }

hpnicfSysSetBootImageResultIndex OBJECT-TYPE
    SYNTAX Integer32 (1..65535)
    MAX-ACCESS not-accessible
    STATUS current
    DESCRIPTION
        "Index of a startup image operation result.  It is identical to the
        entity index of each card."
    ::= { hpnicfSysSetBootImageResultEntry 1 }

hpnicfSysSetBootImageResultStatusOfEachCard OBJECT-TYPE
    SYNTAX INTEGER
        {
        none(1),
        doing(2),
        success(3),
        failed(4)
        }
    MAX-ACCESS read-only
    STATUS current
    DESCRIPTION
        "Status of the startup image set operation."
    ::= { hpnicfSysSetBootImageResultEntry 2 }

hpnicfSysSetBootImageFailedReasonOfEachCard OBJECT-TYPE
    SYNTAX DisplayString (SIZE (0..255))
    MAX-ACCESS read-only
    STATUS current
    DESCRIPTION
        "Reason of the startup image set failure for a card.  It is empty if
        the operation was successful."
    ::= { hpnicfSysSetBootImageResultEntry 3 }
-- End define Boot/Load image table

hpnicfSystemManMIBNotifications OBJECT IDENTIFIER ::= { hpnicfSystemMan 2 }


hpnicfSysClockChangedNotification NOTIFICATION-TYPE
    OBJECTS { hpnicfSysLocalClock }
    STATUS current
    DESCRIPTION
        "
        A clock changed notification is generated when the current
        local date and time for the system has been manually changed.
        The value of hpnicfSysLocalClock reflects new date and time.
        "
    ::= { hpnicfSystemManMIBNotifications 1 }


hpnicfSysReloadNotification NOTIFICATION-TYPE
    OBJECTS { hpnicfSysReloadImage, hpnicfSysReloadCfgFile, hpnicfSysReloadReason, hpnicfSysReloadScheduleTime, hpnicfSysReloadAction
         }
    STATUS current
    DESCRIPTION
        "
        A hpnicfSysReloadNotification will be sent before the corresponding entity is
                        rebooted. It will also be sent if the entity fails to reboot because the clock
                        has changed.
        "
    ::= { hpnicfSystemManMIBNotifications 2 }


    hpnicfSysStartUpNotification NOTIFICATION-TYPE
            OBJECTS { hpnicfSysImageType }
            STATUS current
            DESCRIPTION
            "
            a hpnicfSysStartUpNotification trap will be sent when the system starts up with 'main' image file failed,
            a trap will be sent to indicate which type the current image file (I.e backup or secure)is.
            "
            ::={ hpnicfSystemManMIBNotifications 3}


-- conformance and Compliance define
hpnicfSystemManMIBConformance OBJECT IDENTIFIER ::= { hpnicfSystemMan 3 }


hpnicfSystemManMIBCompliances OBJECT IDENTIFIER ::= { hpnicfSystemManMIBConformance 1 }


hpnicfSystemManMIBCompliance MODULE-COMPLIANCE
    STATUS current
    DESCRIPTION
        "
        The compliance statement for entities which implement
        the system management MIB.
        "
    MODULE -- this module
        MANDATORY-GROUPS { hpnicfSysClockGroup, hpnicfSysReloadGroup, hpnicfSysImageGroup,
                           hpnicfSysCFGFileGroup, hpnicfSystemManNotificationGroup,
                           hpnicfSysCurGroup
             }
        GROUP hpnicfSystemBtmLoadGroup
        DESCRIPTION
        "
        The hpnicfSystemBtmLoadGroup is optional for system.
        "
    ::= { hpnicfSystemManMIBCompliances 1 }


hpnicfSystemManMIBGroups OBJECT IDENTIFIER ::= { hpnicfSystemManMIBConformance 2 }


hpnicfSysClockGroup OBJECT-GROUP
    OBJECTS { hpnicfSysLocalClock, hpnicfSysSummerTimeEnable, hpnicfSysSummerTimeZone, hpnicfSysSummerTimeMethod,
        hpnicfSysSummerTimeStart, hpnicfSysSummerTimeEnd, hpnicfSysSummerTimeOffset }
    STATUS current
    DESCRIPTION
        "A collection of objects providing mandatory system clock information."
    ::= { hpnicfSystemManMIBGroups 1 }


-- A collection of objects providing mandatory system image
-- information.
hpnicfSysReloadGroup OBJECT-GROUP
    OBJECTS { hpnicfSysReloadSchedule, hpnicfSysReloadAction, hpnicfSysReloadImage, hpnicfSysReloadCfgFile, hpnicfSysReloadReason,
        hpnicfSysReloadScheduleTagList,hpnicfSysReloadTag,hpnicfSysReloadScheduleTime, hpnicfSysReloadEntity, hpnicfSysReloadRowStatus }
    STATUS current
    DESCRIPTION
        "A collection of objects providing mandatory system reload."
    ::= { hpnicfSystemManMIBGroups 2 }


hpnicfSysImageGroup OBJECT-GROUP
    OBJECTS { hpnicfSysImageNum, hpnicfSysImageName, hpnicfSysImageSize, hpnicfSysImageLocation,
              hpnicfSysImageType }
    STATUS current
    DESCRIPTION
        "A collection of objects providing mandatory system image information."
    ::= { hpnicfSystemManMIBGroups 3 }


hpnicfSysCFGFileGroup OBJECT-GROUP
    OBJECTS { hpnicfSysCFGFileNum, hpnicfSysCFGFileName, hpnicfSysCFGFileSize, hpnicfSysCFGFileLocation }
    STATUS current
    DESCRIPTION
        "
        A collection of objects providing mandatory system
        configuration file information.
        "
    ::= { hpnicfSystemManMIBGroups 4 }


hpnicfSysCurGroup OBJECT-GROUP
    OBJECTS { hpnicfSysCurCFGFileIndex, hpnicfSysCurImageIndex }
    STATUS current
    DESCRIPTION
        "A collection of system current status."
    ::= { hpnicfSystemManMIBGroups 5 }


hpnicfSystemManNotificationGroup NOTIFICATION-GROUP
    NOTIFICATIONS { hpnicfSysClockChangedNotification, hpnicfSysReloadNotification,
                    hpnicfSysStartUpNotification }
    STATUS current
    DESCRIPTION
        "A collection of notifications."
    ::= { hpnicfSystemManMIBGroups 6 }


hpnicfSystemBtmLoadGroup OBJECT-GROUP
    OBJECTS { hpnicfSysCurBtmFileName, hpnicfSysCurUpdateBtmFileName,
                    hpnicfSysBtmLoadMaxNumber, hpnicfSysBtmFileName,
                    hpnicfSysBtmFileType, hpnicfSysBtmRowStatus,
                    hpnicfSysBtmErrorStatus, hpnicfSysBtmLoadTime }
    STATUS current
    DESCRIPTION
        "A collection of objects providing system update bootrom information."
    ::= { hpnicfSystemManMIBGroups 7 }

END
