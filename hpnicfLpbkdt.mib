-- ==================================================================
-- Copyright (c) 2010-2015 Hewlett-Packard Development Company, L.P.
--
-- Description: Loopback detection MIB
-- Reference:
-- Version: V1.2
-- History:
-- V1.0 2008-09-27 Created by LuoXuefang
-- V1.1 2009-03-30 Added hpnicfLpbkdtTrapPerVlanLoopbacked,
--                 hpnicfLpbkdtTrapPerVlanRecovered and
--                 hpnicfLpbkdtObjects by TongWei.
-- V1.2 2014-07-26 Added hpnicfLpbkdtVlanEnable, hpnicfLpbkdtAction,
--                 hpnicfLpbkdtIntervalTime, hpnicfLpbkdtPortTable,
--                 hpnicfLpbkdtPortEntry, hpnicfLpbkdtPortIfIndex,
--                 hpnicfLpbkdtPortVlanEnable, hpnicfLpbkdtPortAction and
--                 hpnicfLpbkdtPortLoopbacked by ZhangWei.
-- ==================================================================
HPN-ICF-LPBKDT-MIB DEFINITIONS ::= BEGIN

IMPORTS
    hpnicfCommon
        FROM HPN-ICF-OID-MIB
    ifIndex, ifDescr
        FROM IF-MIB
    VlanId
        FROM Q-BRIDGE-MIB
    TEXTUAL-CONVENTION, TruthValue
        FROM SNMPv2-TC
    OBJECT-TYPE, MODULE-IDENTITY, NOTIFICATION-TYPE, Integer32
        FROM SNMPv2-SMI
    InterfaceIndex
        FROM IF-MIB;

hpnicfLpbkdt MODULE-IDENTITY
    LAST-UPDATED "201407261518Z"        -- July 26, 2014 at 15:18 GMT
    ORGANIZATION
        ""
    CONTACT-INFO
        ""
    DESCRIPTION
        "Loops may cause broadcast storms.  The purpose of loopback detection
         is to detect loops on the device and to protect the network."

    REVISION "201407261518Z"
    DESCRIPTION
        "Added new nodes to configure the loop detection."
    REVISION "200903301741Z"
    DESCRIPTION
        "To fix bugs in the MIB file."
    REVISION "200809271504Z"
    DESCRIPTION
        "The initial revision of this MIB module."
    ::= { hpnicfCommon 95 }

-- ==================================================================
--
-- ======================= definition begin =========================
--
-- ==================================================================

HpnicfLpbkdtActionType ::= TEXTUAL-CONVENTION
    STATUS current
    DESCRIPTION
        "Loopback detection action on the port on which a loop is detected.
        When a loop is detected on a port, the device generates a log.  The
        enumeration 'none(1)' means that the device performs no action on the
        port.  The enumeration 'block(2)' means that the device disables MAC
        address learning and blocks traffic on the port.  The enumeration
        'nolearning(3)' means that the device disables MAC address learning on
        the port.  The enumeration 'shutdown(4)' means that the device shuts
        down the port.  The device automatically sets the port to the forwarding
        state after the time interval configured."
    SYNTAX  INTEGER {
            none(1),
            block(2),
            nolearning(3),
            shutdown(4)
    }

hpnicfLpbkdtNotifications OBJECT IDENTIFIER ::= { hpnicfLpbkdt 1 }
hpnicfLpbkdtObjects       OBJECT IDENTIFIER ::= { hpnicfLpbkdt 2 }
hpnicfLpbkdtTrapPrefix    OBJECT IDENTIFIER ::= { hpnicfLpbkdtNotifications 0 }

hpnicfLpbkdtTrapLoopbacked NOTIFICATION-TYPE
    OBJECTS { ifIndex, ifDescr }
    STATUS current
    DESCRIPTION
        "Trap message is generated when the interface is looped."
    ::= { hpnicfLpbkdtTrapPrefix 1 }

hpnicfLpbkdtTrapRecovered NOTIFICATION-TYPE
    OBJECTS { ifIndex, ifDescr }
    STATUS current
    DESCRIPTION
        "Trap message is generated when the loops on the interface
         are eliminated."
    ::= { hpnicfLpbkdtTrapPrefix 2 }

hpnicfLpbkdtTrapPerVlanLoopbacked NOTIFICATION-TYPE
    OBJECTS { ifIndex, ifDescr, hpnicfLpbkdtVlanID }
    STATUS current
    DESCRIPTION
        "Trap message is generated when the interface is looped in the VLAN."
    ::= { hpnicfLpbkdtTrapPrefix 3 }

hpnicfLpbkdtTrapPerVlanRecovered NOTIFICATION-TYPE
    OBJECTS { ifIndex, ifDescr, hpnicfLpbkdtVlanID }
    STATUS current
    DESCRIPTION
        "Trap message is generated when the loop on the interface
         is eliminated in the VLAN."
    ::= { hpnicfLpbkdtTrapPrefix 4 }

hpnicfLpbkdtVlanID OBJECT-TYPE
    SYNTAX      VlanId
    MAX-ACCESS  accessible-for-notify
    STATUS      current
    DESCRIPTION
        "The ID of VLAN."
    ::= { hpnicfLpbkdtObjects 1 }

hpnicfLpbkdtVlanEnable OBJECT-TYPE
    SYNTAX      OCTET STRING(SIZE(512))
    MAX-ACCESS  read-write
    STATUS      current
    DESCRIPTION
       "Whether the loop detection is enabled globally for the VLANs.  Each
       octet within this value specifies a set of eight VLANs, with the first
       octet specifying VLANs 1 through 8, the second octet specifying VLANs 9
       through 16, etc.  Within each octet, the most significant bit represents
       the highest numbered VLAN, and the least significant bit represents the
       lowest numbered VLAN.  Thus, each VLAN is represented by a single bit
       within the value of this object.  A bit with a value of '1' indicates
       that the loop detection is enabled globally for the VLAN; the loop
       detection is disabled globally for the VLAN if its bit has a value of
       '0'.  The 4095th and 4096th bits must be have a value of '0'."
    ::= { hpnicfLpbkdtObjects 2 }

hpnicfLpbkdtAction OBJECT-TYPE
    SYNTAX      HpnicfLpbkdtActionType
    MAX-ACCESS  read-write
    STATUS      current
    DESCRIPTION
        "Global loopback detection action on the port on which a loop is
        detected.  The global action applies to all ports.  The per-port action
        takes precedence over the global action."
    DEFVAL      { none }
    ::= { hpnicfLpbkdtObjects 3 }

hpnicfLpbkdtIntervalTime OBJECT-TYPE
    SYNTAX      Integer32(1..300)
    MAX-ACCESS  read-write
    STATUS      current
    DESCRIPTION
        "The interval at which loop detection frames are transmitted."
    DEFVAL      { 30 }
    ::= { hpnicfLpbkdtObjects 4 }

hpnicfLpbkdtPortTable OBJECT-TYPE
    SYNTAX      SEQUENCE OF HpnicfLpbkdtPortEntry
    MAX-ACCESS  not-accessible
    STATUS      current
    DESCRIPTION
        "A table containing information about the loop detection configurations
        and status for individual ports."
    ::= { hpnicfLpbkdtObjects  5 }

hpnicfLpbkdtPortEntry OBJECT-TYPE
    SYNTAX      HpnicfLpbkdtPortEntry
    MAX-ACCESS  not-accessible
    STATUS      current
    DESCRIPTION
        "Detailed information of a specified port."
    INDEX   { hpnicfLpbkdtPortIfIndex }
    ::= { hpnicfLpbkdtPortTable 1 }

HpnicfLpbkdtPortEntry  ::= SEQUENCE
    {
        hpnicfLpbkdtPortIfIndex       InterfaceIndex,
        hpnicfLpbkdtPortVlanEnable    OCTET STRING,
        hpnicfLpbkdtPortAction        HpnicfLpbkdtActionType,
        hpnicfLpbkdtPortLoopbacked    TruthValue
    }

hpnicfLpbkdtPortIfIndex OBJECT-TYPE
    SYNTAX      InterfaceIndex
    MAX-ACCESS  not-accessible
    STATUS      current
    DESCRIPTION
        "The ifIndex of the port."
    ::={ hpnicfLpbkdtPortEntry 1 }

hpnicfLpbkdtPortVlanEnable OBJECT-TYPE
    SYNTAX      OCTET STRING(SIZE(512))
    MAX-ACCESS  read-write
    STATUS      current
    DESCRIPTION
        "Whether the loop detection is enabled on the port for the VLANs.  Each
        octet within this value specifies a set of eight VLANs, with the first
        octet specifying VLANs 1 through 8, the second octet specifying VLANs 9
        through 16, etc.  Within each octet, the most significant bit represents
        the highest numbered VLAN, and the least significant bit represents the
        lowest numbered VLAN.  Thus, each VLAN is represented by a single bit
        within the value of this object.  A bit with a value of '1' indicates
        that the loop detection is enabled on the port for the VLAN; the loop
        detection is disabled on the port for the VLAN if its bit has a value of
        '0'.  The 4095th and 4096th bits must be have a value of '0'."
    ::={ hpnicfLpbkdtPortEntry 2 }

hpnicfLpbkdtPortAction OBJECT-TYPE
    SYNTAX      HpnicfLpbkdtActionType
    MAX-ACCESS  read-write
    STATUS      current
    DESCRIPTION
        "Loopback detection action on the port on which a loop is detected.  The
        per-port action takes precedence over the global action."
    ::={ hpnicfLpbkdtPortEntry 3 }

hpnicfLpbkdtPortLoopbacked OBJECT-TYPE
    SYNTAX      TruthValue
    MAX-ACCESS  read-only
    STATUS      current
    DESCRIPTION
        "Whether the port is looped."
    ::={ hpnicfLpbkdtPortEntry 4 }

END
