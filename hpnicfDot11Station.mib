-- =============================================================================
-- Copyright (c) 2010-2016 Hewlett-Packard Development Company, L.P.
--
-- Description:
--   The file defines a MIB to provide 802.11 MAC information such
--   as station statistic and notification events.
-- Reference:
-- Version: V2.9
-- History:
--   V1.0 created by shiyang (Richard)
--     Initial version 2006-05-10
--   V1.1 2007-04-27 modified by shiyang(Richard)
--        The data type of object hpnicfDot11StationRxFrameBytes,
--        hpnicfDot11StationTxFrameBytes and hpnicfDot11StationDropFrameBytes
--        was changed from counter32 to counter64.
--   V1.2 2007-06-21 modified by Vikas K
--        Added 4 new Station Traps and also new objects for the traps.
--   V1.3 2007-12-21 modified by wanghao (Kumar)
--        Added hpnicfDot11StationRxSNR, hpnicfDot11StationTxRate,
--        hpnicfDot11StationRxRate to hpnicfDot11StationAssociateTable.
--        Added hpnicfDot11StationSessionDuration to hpnicfDot11StationDeAssocTrap
--        Added hpnicfDot11StationSessionDuration to hpnicfDot11StationTrapVarObjects.
--        Added hpnicfDot11StationVendorName and hpnicfDot11StationRadioMode to
--        HpnicfDot11StationAssociateEntry.
--   V1.4 2008-02-25 modified by wanghao (Kumar)
--        Add hpnicfDot11StationRoamingTrap and add hpnicfDot11StationRxNoise to
--        hpnicfDot11StationAssociateTable.
--   V1.5 2008-08-01 modified by Wang Lu
--        Change description of hpnicfDot11StationMAC, hpnicfDot11CurrWlanID and
--        hpnicfDot11StationAid.
--        Change SYNTAX of hpnicfDot11StationSessionStartTime
--        Change OBJECTS of hpnicfDot11StationAuthorFailTrap,
--        hpnicfDot11StationAssocFailTrap, hpnicfDot11StationDeAssocTrap and
--        hpnicfDot11StationAuthorSuccTrap
--   V1.6 2008-11-07 modified by Wang Lu and Li Yugang
--        Add hpnicfDot11StationRxRetryPkts, hpnicfDot11StationTxRetryPkts,
--        hpnicfDot11StationRxRetryBytes and hpnicfDot11StationTxRetryBytes
--        to hpnicfDot11StationStatisTable.
--        Add new variable bindings hpnicfDot11StationAPName and
--        hpnicfDot11StationBSSID to hpnicfDot11StationAuthorSuccTrap and
--        hpnicfDot11StationDeAssocTrap.
--        Add new notification hpnicfDot11StationDisconnectTrap.
--        Add hpnicfDot11StationThroughput to hpnicfDot11StationStatisTable.
--   V1.7 2009-05-07 modified by Wang Shaojie
--        Add hpnicfDot11StationMACAddress to hpnicfDot11StationAssociateTable
--   V1.8 2009-04-14 modified by Heziqi
--        Add new node hpnicfDot11StationSuccessTxCnt, hpnicfDot11StationRxFragCnt
--        and hpnicfDot11StationSuccessTxDataCnt for hpnicfDot11StationStatisTable.
--        Add new node hpnicfDot11StationTxSpeed, hpnicfDot11StationRxSpeed
--        and hpnicfDot11StationWmmMode for hpnicfDot11StationAssociateTable.
--        Add new node hpnicfDot11StationRxDataFrameCnt,
--        hpnicfDot11StationTxDataFrameCnt, hpnicfDot11StationRxDataFrameBytes
--        hpnicfDot11StationTxDataFrameBytes for hpnicfDot11StationAssociateTable.
--   V1.9 2009-08-07 modified by Wang Shaojie
--        Modify description of hpnicfDot11StationTxSpeed, hpnicfDot11StationRxSpeed
--   V2.0 2010-02-23 Add new node hpnicfDot11StaRxErrDataFrameCnt and
--        hpnicfDot11StaTxRetryDataFrameCnt to hpnicfDot11StationStatisTable.
--        Add new node hpnicfDot11StationUpTimeTicks, hpnicfDot11StationSecIEStatus
--        to hpnicfDot11StationAssociateTable.
--        Add hpnicfDot11StationAuthMode to hpnicfDot11StationTrapVarObjects.
--        2010-08-07 modified by Wang Shaojie
--        Add hpnicfDot11StationACIPv6Add to hpnicfDot11StationTrapVarObjects.
--        2010-09-02 modified by Yin junjie
--        Modify hpnicfDot11StationDisconnectTrap.
--   V2.1 2011-08-10 modified by limingjin
--        Add hpnicfDot11StationRadioMode2 to hpnicfDot11StationAssociateTable
--   V2.2 2011-09-28 modified by zhanghu
--        Add hpnicfDot11StaTxDataRatePkts, hpnicfDot11StaRxDataRatePkts,
--        hpnicfDot11StaTxSignalStrengthPkts to hpnicfDot11StationStatisTable
--        2012-02-08 modified by d07436
--        Add hpnicfDot11StationAssTime to  hpnicfDot11StationAssociateEntry
--        Add hpnicfDot11UserDisconnectTrap to hpnicfDot11StationTraps
--        Add hpnicfDot11UserName to hpnicfDot11StationTrapVarObjects
--   V2.3 2012-05-16 modified by lihonghao
--        Add hpnicfDot11StationUserAuthType to hpnicfDot11StationAssociateTable
--        2012-08-13 modified by wangminghui
--        Add new node   hpnicfDot11StationTrapAPMacAddress to hpnicfDot11StationTrapVarObjects
--        Add new object hpnicfDot11StationTrapAPMacAddress to hpnicfDot11StationAuthorFailTrap
--        Add new object hpnicfDot11StationTrapAPMacAddress to hpnicfDot11StationAssocFailTrap
--        modified by niujian
--        Add hpnicfDot11StationRfPingTest to hpnicfDot11StationAssociateTable.
--        Add hpnicfDot11StationRfPingTable.
--   V2.4 2013-04-10 modified by huashuyuan
--        Add hpnicfDot11StationMaxRate to hpnicfDot11StationAssociateTable
--   V2.5 2013-08-21 modified by zhangsiyu
--        Add hpnicfDot11CurrAntennaID to hpnicfDot11StationAPRelationTable
--   V2.6 2014-02-13 modified by xiaomin
--        Add hpnicfDot11StationPowerSaveModeCM, hpnicfDot11StationAuthenModeCM,
--        hpnicfDot11StationAKMModeCM, hpnicfDot11StationSecurityCiphersCM
--        and hpnicfDot11StationSecIEStatusCM to hpnicfDot11StationAssociateTable
--   V2.7 2014-05-08 modified by yubo
--        Add hpnicfDot11StaInternetRxFrameBytes,hpnicfDot11StaInternetTxFrameBytes,
--        hpnicfDot11StaLocalRxFrameBytes,hpnicfDot11StaLocalTxFrameBytes to
--        hpnicfDot11StationStatisTable.
--   V2.8 2014-11-19 modified by yubo
--        Add hpnicfDot11StationIPv6Address to hpnicfDot11StationAssociateTable
--   V2.9 2015-04-13 modified by limingjin
--        Add hpnicfDot11StaAntennaChgTrap to hpnicfDot11StationTraps
--        Add new node   hpnicfDot11StationTrapOldAntennaID to hpnicfDot11StationTrapVarObjects
--        Add new node   hpnicfDot11StationTrapNewAntennaID to hpnicfDot11StationTrapVarObjects
-- =============================================================================
HPN-ICF-DOT11-STATION-MIB DEFINITIONS ::= BEGIN

IMPORTS
        MacAddress, DateAndTime, TruthValue
    FROM SNMPv2-TC
        MODULE-IDENTITY,
        OBJECT-TYPE,
        NOTIFICATION-TYPE,
        Integer32,
        Unsigned32,
        Counter32,
        Counter64,
        IpAddress,
        TimeTicks
    FROM SNMPv2-SMI
        hpnicfDot11,
        HpnicfDot11RadioType,
        HpnicfDot11ObjectIDType,
        HpnicfDot11ChannelScopeType,
        HpnicfDot11SSIDStringType,
        HpnicfDot11AuthenType,
        HpnicfDot11AKMType,
        HpnicfDot11CipherType,
        HpnicfDot11RadioScopeType,
        HpnicfDot11SSIDEncryptModeType,
        HpnicfDot11AssocFailType,
        HpnicfDot11AuthorFailType,
        HpnicfDot11SecIEStatusType,
        HpnicfDot11RadioType2
    FROM HPN-ICF-DOT11-REF-MIB;

hpnicfDot11STATION MODULE-IDENTITY
    LAST-UPDATED "201504131800Z"        -- Apr 13, 2015 at 18:00 GMT
    ORGANIZATION
        ""
    CONTACT-INFO
        ""
    DESCRIPTION
        "This MIB defines the configuration and statistic information of
        stations.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Control And Provisioning of Wireless Access Points Protocol
        The short name of protocol is CAPWAP.  AC will control
        and manage AP by CAPWAP tunnel protocol defined by IETF.
        Also, a data tunnel will be set up between AC and AP.

        BSS
        IEEE 802.11 Basic Service Set (Radio Cell).  The
        BSS of an AP comprises of the stations directly
        associated with the AP.

        station (Client Station)
        A wireless device in a wireless network
        associated with an access point.

        MIC
        Message Integrity Check.  A MIC can, optionally,
        be added to WEP-encrypted 802.11 frames.

        SSID
        Radio Service Set ID.  It is used for identification
        during association.

        STA  (WSTA)
        A non-AP 802.11 wireless station.

        WEP
        Wired Equivalent Privacy.  'WEP' is generally used
        to refer to 802.11 encryption.

        RSSI
        It is the received signal strength indication.
        It suggests the quality of received signal.

        RTS
        Request to Send, it is used to gain control of the medium
        for the transmission of 'large' frames, in which 'large'
        is defined by the RTS threshold in the network card driver.

        CTS
        Clear to Send, it is used to answer RTS frames.

        AKM
        The authentication and key management method defined by
        802.11i, and which includes 802.1x and pre-shared key."

    REVISION "201504131800Z"        -- Apr 13, 2015 at 18:00 GMT
    DESCRIPTION
        "Add hpnicfDot11StaAntennaChgTrap to hpnicfDot11StationTraps
         Add new node hpnicfDot11StationTrapOldAntennaID to hpnicfDot11StationTrapVarObjects
         Add new node hpnicfDot11StationTrapNewAntennaID to hpnicfDot11StationTrapVarObjects"
    REVISION "201009021800Z"        -- Sep 2, 2010 at 18:00 GMT
    DESCRIPTION
        "Modify hpnicfDot11StationDisconnectTrap."
    REVISION "201002231800Z"        -- Feb 23, 2010 at 18:00 GMT
    DESCRIPTION
        "Add new node hpnicfDot11StationUpTimeTicks, hpnicfDot11StationSecIEStatus
         to hpnicfDot11StationAssociateTable."
    REVISION "200912011800Z"        -- Aug 07, 2009 at 18:00 GMT
    DESCRIPTION
        "Add new node hpnicfDot11StaRxErrDataFrameCnt and hpnicfDot11StaTxRetryDataFrameCnt
         to hpnicfDot11StationStatisTable"
    REVISION "200908071800Z"        -- Aug 07, 2009 at 18:00 GMT
    DESCRIPTION
        "Modify description of hpnicfDot11StationTxSpeed, hpnicfDot11StationRxSpeed"
    REVISION "200907291800Z"        -- Jul 29, 2009 at 18:00 GMT
    DESCRIPTION
        "Modified to add new nodes."
    REVISION "200905072000Z"        -- May 7, 2009 at 20:00 GMT
    DESCRIPTION
        "Modified to add new nodes."
    REVISION "200811071730Z"        -- Nov 07, 2008 at 17:30 GMT
    DESCRIPTION
        "Modified to add new nodes."
    REVISION "200802251800Z"        -- Feb 25, 2008 at 18:00 GMT
    DESCRIPTION
        "Modified to add new trap and add hpnicfDot11StationRxNoise to hpnicfDot11StationAssociateTable."
    REVISION "200712211800Z"        -- Dec 21, 2007 at 18:00 GMT
    DESCRIPTION
        "Modified to add new nodes."
    REVISION "200706212000Z"        -- Jun 21, 2007 at 20:00 GMT
    DESCRIPTION
        "Changes made for new requirements."
    REVISION "200704272000Z"        -- Apr 27, 2007 at 20:00 GMT
    DESCRIPTION
        "Modified to fix some issue."
    REVISION "200605101600Z"        -- May 10, 2006 at 19:00 GMT
    DESCRIPTION
        "The initial revision of this MIB module."
    ::= { hpnicfDot11 3 }

-- *****************************************************************************
-- *  Major sections
-- *****************************************************************************
--  Station Management Group
--  DEFINED AS "The group to provide the basic information for station,
--  for example, associated station, performance data and so on."

hpnicfDot11StationMtGroup OBJECT IDENTIFIER     ::= { hpnicfDot11STATION 1 }
--  Station Management Group has the following children:
--  hpnicfDot11StationAssociateTable            ::= { hpnicfDot11APMtGroup 1 }
--  hpnicfDot11StationAPRelationTable           ::= { hpnicfDot11APMtGroup 2 }
--  hpnicfDot11StationStatisTable               ::= { hpnicfDot11APMtGroup 3 }
--  hpnicfDot11StationRfPingTable               ::= { hpnicfDot11APMtGroup 4 }

--  MAC Event Notification
--  DEFINED AS "The group to provide station notification information"
hpnicfDot11StationNotifyGroup OBJECT IDENTIFIER ::= { hpnicfDot11STATION 2 }

-- *****************************************************************************
-- *  hpnicfDot11StaAssociateTable Definition
-- *****************************************************************************
hpnicfDot11StationAssociateTable OBJECT-TYPE
    SYNTAX      SEQUENCE OF HpnicfDot11StationAssociateEntry
    MAX-ACCESS  not-accessible
    STATUS      current
    DESCRIPTION
        "This table contains the information of stations which are
        associating with the wireless network (current AC)."
    ::= { hpnicfDot11StationMtGroup 1 }

hpnicfDot11StationAssociateEntry OBJECT-TYPE
    SYNTAX      HpnicfDot11StationAssociateEntry
    MAX-ACCESS  not-accessible
    STATUS      current
    DESCRIPTION
        "Each entry contains association information of each station."
    INDEX
        {
            hpnicfDot11StationMAC
        }
    ::= { hpnicfDot11StationAssociateTable 1 }

HpnicfDot11StationAssociateEntry ::= SEQUENCE
    {
        hpnicfDot11StationMAC                MacAddress,
        hpnicfDot11StationIPAddress          IpAddress,
        hpnicfDot11StationUserName           OCTET STRING,
        hpnicfDot11StationTxRateSet          OCTET STRING,
        hpnicfDot11StationUpTime             Unsigned32,
        hpnicfDot11StationSignalStrength     Integer32,
        hpnicfDot11StationRSSI               Integer32,
        hpnicfDot11StationChannel            HpnicfDot11ChannelScopeType,
        hpnicfDot11StationPowerSaveMode      INTEGER,
        hpnicfDot11StationAid                Integer32,
        hpnicfDot11StationVlanId             Integer32,
        hpnicfDot11StationSSIDName           HpnicfDot11SSIDStringType,
        hpnicfDot11StationAuthenMode         HpnicfDot11AuthenType,
        hpnicfDot11StationAKMMode            HpnicfDot11AKMType,
        hpnicfDot11StationSecurityCiphers    HpnicfDot11CipherType,
        hpnicfDot11StationSSIDEncryptMode    HpnicfDot11SSIDEncryptModeType,
        hpnicfDot11StationRxSNR              Integer32,
        hpnicfDot11StationTxRate             Integer32,
        hpnicfDot11StationRxRate             Integer32,
        hpnicfDot11StationVendorName         OCTET STRING,
        hpnicfDot11StationRadioMode          HpnicfDot11RadioType,
        hpnicfDot11StationRxNoise            Integer32,
        hpnicfDot11StationMACAddress         MacAddress,
        hpnicfDot11StationTxSpeed            Integer32,
        hpnicfDot11StationRxSpeed            Integer32,
        hpnicfDot11StationWmmMode            INTEGER,
        hpnicfDot11StationSecIEStatus        HpnicfDot11SecIEStatusType,
        hpnicfDot11StationUpTimeTicks        TimeTicks,
        hpnicfDot11StationRadioMode2         HpnicfDot11RadioType2,
        hpnicfDot11StationAssTime            DateAndTime,
        hpnicfDot11StationUserAuthType       INTEGER,
        hpnicfDot11StationRfPingTest         TruthValue,
        hpnicfDot11StationMaxRate            Integer32,
        hpnicfDot11StationPowerSaveModeCM    INTEGER,
        hpnicfDot11StationAuthenModeCM       INTEGER,
        hpnicfDot11StationAKMModeCM          INTEGER,
        hpnicfDot11StationSecurityCiphersCM  INTEGER,
        hpnicfDot11StationSecIEStatusCM      INTEGER,
        hpnicfDot11StationIPv6Address        OCTET STRING
    }

hpnicfDot11StationMAC OBJECT-TYPE
    SYNTAX      MacAddress
    MAX-ACCESS  not-accessible
    STATUS      current
    DESCRIPTION
        "Represents the unique MAC Address of station."
    ::= { hpnicfDot11StationAssociateEntry 1 }

hpnicfDot11StationIPAddress OBJECT-TYPE
    SYNTAX      IpAddress
    MAX-ACCESS  read-only
    STATUS      current
    DESCRIPTION
        "Represents the IP address of the station."
    ::= { hpnicfDot11StationAssociateEntry 2 }

hpnicfDot11StationUserName OBJECT-TYPE
    SYNTAX      OCTET STRING
    MAX-ACCESS  read-only
    STATUS      current
    DESCRIPTION
        "Represents the user name of the station."
    ::= { hpnicfDot11StationAssociateEntry 3 }

hpnicfDot11StationTxRateSet OBJECT-TYPE
    SYNTAX      OCTET STRING
    UNITS       "Mbps"
    MAX-ACCESS  read-only
    STATUS      current
    DESCRIPTION
        "Represents the current transmit data rates for this station.
        Each byte will represent one rate.  If the MSB(Most significant bit)
        is set, then this rate is a mandantory rate.  Otherwise,
        it is optional."
    ::= { hpnicfDot11StationAssociateEntry 4 }

hpnicfDot11StationUpTime OBJECT-TYPE
    SYNTAX      Unsigned32
    UNITS       "second"
    MAX-ACCESS  read-only
    STATUS      current
    DESCRIPTION
        "The time in seconds, how long this station has been associated
        with this device."
    ::= { hpnicfDot11StationAssociateEntry 5 }

hpnicfDot11StationSignalStrength OBJECT-TYPE
    SYNTAX      Integer32
    UNITS       "dBm"
    MAX-ACCESS  read-only
    STATUS      current
    DESCRIPTION
        "Represents a device-dependent measure of the signal strength
        of latest packet received from this station."
    ::= { hpnicfDot11StationAssociateEntry 6 }

hpnicfDot11StationRSSI OBJECT-TYPE
    SYNTAX      Integer32
    MAX-ACCESS  read-only
    STATUS      current
    DESCRIPTION
        "Represents a device-dependent measure of the RSSI.
        It is the received signal strength indication.
        The maximum value is defined by chip set vendors"
    ::= { hpnicfDot11StationAssociateEntry 7 }

hpnicfDot11StationChannel OBJECT-TYPE
    SYNTAX      HpnicfDot11ChannelScopeType
    MAX-ACCESS  read-only
    STATUS      current
    DESCRIPTION
        "Represents current radio channel used by station."
    ::= { hpnicfDot11StationAssociateEntry 8 }

hpnicfDot11StationPowerSaveMode OBJECT-TYPE
    SYNTAX      INTEGER
        {
            active(1),
            powersave(2)
        }
    MAX-ACCESS  read-only
    STATUS      current
    DESCRIPTION
        "Represents the power management mode of this station.
        The following values are supported:
        active    - This station is not in power-save
        mode and it is actively sending or
        receiving data.
        powersave - This station is in power-save mode and
        it wakes up after sometime to check for
        buffer data."
    DEFVAL      { active }
    ::= { hpnicfDot11StationAssociateEntry 9 }

hpnicfDot11StationAid OBJECT-TYPE
    SYNTAX      Integer32
    MAX-ACCESS  read-only
    STATUS      current
    DESCRIPTION
        "Represents the association identification number of station."
    ::= { hpnicfDot11StationAssociateEntry 10 }

hpnicfDot11StationVlanId OBJECT-TYPE
    SYNTAX      Integer32
    MAX-ACCESS  read-only
    STATUS      current
    DESCRIPTION
        "Represents Vlan ID to which the station is associated."
    ::= { hpnicfDot11StationAssociateEntry 11 }

hpnicfDot11StationSSIDName OBJECT-TYPE
    SYNTAX      HpnicfDot11SSIDStringType
    MAX-ACCESS  read-only
    STATUS      current
    DESCRIPTION
        "Represents the ESS name."
    ::= { hpnicfDot11StationAssociateEntry 12 }

hpnicfDot11StationAuthenMode OBJECT-TYPE
    SYNTAX      HpnicfDot11AuthenType
    MAX-ACCESS  read-only
    STATUS      current
    DESCRIPTION
        "Represents the Authentication mode defined by 802.11."
    ::= { hpnicfDot11StationAssociateEntry 13 }

hpnicfDot11StationAKMMode OBJECT-TYPE
    SYNTAX      HpnicfDot11AKMType
    MAX-ACCESS  read-only
    STATUS      current
    DESCRIPTION
        "Represents the key management mode defined by 802.11i."
    ::= { hpnicfDot11StationAssociateEntry 14 }

hpnicfDot11StationSecurityCiphers OBJECT-TYPE
    SYNTAX      HpnicfDot11CipherType
    MAX-ACCESS  read-only
    STATUS      current
    DESCRIPTION
        "Represents the frame encryption cipher type used by
        station."
    ::= { hpnicfDot11StationAssociateEntry 15 }

hpnicfDot11StationSSIDEncryptMode OBJECT-TYPE
    SYNTAX      HpnicfDot11SSIDEncryptModeType
    MAX-ACCESS  read-only
    STATUS      current
    DESCRIPTION
        "Represents the encryption mode for this ESS."
    DEFVAL      { cipher }
    ::= { hpnicfDot11StationAssociateEntry 16 }

hpnicfDot11StationRxSNR OBJECT-TYPE
    SYNTAX      Integer32
    UNITS       "One Percent"
    MAX-ACCESS  read-only
    STATUS      current
    DESCRIPTION
        "Represents the signal and noise strength ratio of frame reception."
    ::= { hpnicfDot11StationAssociateEntry 17 }

hpnicfDot11StationTxRate OBJECT-TYPE
    SYNTAX      Integer32
    UNITS       "Mbps"
    MAX-ACCESS  read-only
    STATUS      current
    DESCRIPTION
        "Represents the transmission rate of frame."
    ::= { hpnicfDot11StationAssociateEntry 18 }

hpnicfDot11StationRxRate OBJECT-TYPE
    SYNTAX      Integer32
    UNITS       "Mbps"
    MAX-ACCESS  read-only
    STATUS      current
    DESCRIPTION
        "Represents the reception rate of frame."
    ::= { hpnicfDot11StationAssociateEntry 19 }

hpnicfDot11StationVendorName OBJECT-TYPE
    SYNTAX      OCTET STRING(SIZE(0..127))
    MAX-ACCESS  read-only
    STATUS      current
    DESCRIPTION
        "Represents the vendor name of the station."
    ::= { hpnicfDot11StationAssociateEntry 20 }

hpnicfDot11StationRadioMode OBJECT-TYPE
    SYNTAX      HpnicfDot11RadioType
    MAX-ACCESS  read-only
    STATUS      current
    DESCRIPTION
        "Represents which radio type supported by the station.
        The WLAN system support the following possible radio types.
        dot11a(1),
        dot11b(2),
        dot11g(4),
        dot11n(8)
        For a station,it could support only one radio type at
        the same time."
    ::= { hpnicfDot11StationAssociateEntry 21 }

hpnicfDot11StationRxNoise OBJECT-TYPE
    SYNTAX      Integer32
    MAX-ACCESS  read-only
    STATUS      current
    DESCRIPTION
        "Represents the received noise of the station."
    ::= { hpnicfDot11StationAssociateEntry 22 }


hpnicfDot11StationMACAddress OBJECT-TYPE
    SYNTAX      MacAddress
    MAX-ACCESS  read-only
    STATUS      current
    DESCRIPTION
        "Represents MAC Address of station."
    ::= { hpnicfDot11StationAssociateEntry 23 }

hpnicfDot11StationTxSpeed OBJECT-TYPE
    SYNTAX      Integer32
    UNITS       "byte/s"
    MAX-ACCESS  read-only
    STATUS      current
    DESCRIPTION
        "Represents the bytes of transmitted data frames to the
        station per second in sample interval."
    ::= { hpnicfDot11StationAssociateEntry 24 }

hpnicfDot11StationRxSpeed OBJECT-TYPE
    SYNTAX      Integer32
    UNITS       "byte/s"
    MAX-ACCESS  read-only
    STATUS      current
    DESCRIPTION
        "Represents the bytes of received data frames from the
        station per second in sample interval."
    ::= { hpnicfDot11StationAssociateEntry 25 }

hpnicfDot11StationWmmMode  OBJECT-TYPE
    SYNTAX      INTEGER
        {
            wmm(1),
            nonwmm(2)
        }
    MAX-ACCESS  read-only
    STATUS      current
    DESCRIPTION
        "Represents the QoS mode of station.
        The following values are supported:
        wmm    - This QoS function is supported by this station.
        nonwmm - This QoS function is not supported by this station."
    ::= { hpnicfDot11StationAssociateEntry 26 }

hpnicfDot11StationSecIEStatus OBJECT-TYPE
    SYNTAX      HpnicfDot11SecIEStatusType
    MAX-ACCESS  read-only
    STATUS      current
    DESCRIPTION
        "Represents the security Information element for this station."
    ::= { hpnicfDot11StationAssociateEntry 27 }

hpnicfDot11StationUpTimeTicks OBJECT-TYPE
    SYNTAX      TimeTicks
    MAX-ACCESS  read-only
    STATUS      current
    DESCRIPTION
        "Represents how long this station has been associated
         with this device."
    ::= { hpnicfDot11StationAssociateEntry 28 }

hpnicfDot11StationRadioMode2 OBJECT-TYPE
    SYNTAX      HpnicfDot11RadioType2
    MAX-ACCESS  read-only
    STATUS      current
    DESCRIPTION
        "Represents which radio type supported by the station.
        The WLAN system support the following possible radio types.
        dot11a(1),
        dot11b(2),
        dot11g(4),
        dot11an(8),
        dot11gn(16)
        For a station,it could support only one radio type at
        the same time."
    ::= { hpnicfDot11StationAssociateEntry 29 }

hpnicfDot11StationAssTime OBJECT-TYPE
    SYNTAX      DateAndTime
    MAX-ACCESS  read-only
    STATUS      current
    DESCRIPTION
        "Represents the time at which the station connected."
    ::= { hpnicfDot11StationAssociateEntry 30 }

hpnicfDot11StationUserAuthType OBJECT-TYPE
    SYNTAX      INTEGER
        {
            portalAuth(1),
            authFree(2),
            associateAuth(3),
            macAuth(4)
        }
    MAX-ACCESS  read-only
    STATUS      current
    DESCRIPTION
        "Represents the type of user authentication with this station.
        portalAuth    - The authentication lunched by portal pop-up program
        which is need input username and passward,exclude MAC authentication.
        authFree      - There is no need others authentiaction,user will
        surf internet after association.
        associateAuth - Include WEP PSK 802.1X authentication.
        macAuth       - MAC Authentication apply with access device,
        a Remote Authentication Dial-In User Service (RADIUS) server or
        message netgate to realize fast authentication."
    ::= { hpnicfDot11StationAssociateEntry 31 }

hpnicfDot11StationRfPingTest OBJECT-TYPE
    SYNTAX      TruthValue
    MAX-ACCESS  read-write
    STATUS      current
    DESCRIPTION
        "This object is used to start rfping test of the station.
         It will return false for get operation."
    ::= { hpnicfDot11StationAssociateEntry 32 }

hpnicfDot11StationMaxRate OBJECT-TYPE
    SYNTAX      Integer32
    UNITS       "Mbps"
    MAX-ACCESS  read-only
    STATUS      current
    DESCRIPTION
        "Represents the max negotiation rate of the station."
    ::= { hpnicfDot11StationAssociateEntry 33 }

hpnicfDot11StationPowerSaveModeCM OBJECT-TYPE
    SYNTAX      INTEGER
        {
            active(0),
            powersave(1)
        }
    MAX-ACCESS  read-only
    STATUS      current
    DESCRIPTION
        "Represents the power management mode of the client.
        The following values are supported:
        active    - This client is not in power-save
        mode and it is actively sending or receiving data.
        powersave - This client is in power-save mode and
        it wakes up after some time to check for buffer data."
    DEFVAL      { active }
    ::= { hpnicfDot11StationAssociateEntry 34 }

hpnicfDot11StationAuthenModeCM OBJECT-TYPE
    SYNTAX      INTEGER
        {
            opensystem(0),
            sharedkey(1)
        }
    MAX-ACCESS  read-only
    STATUS      current
    DESCRIPTION
        "Represents the authentication mode defined by 802.11.
        The following values are supported:
        opensystem   - Do not authenticate.
        sharedkey    - System will use challenge message to
        authenticate the client."
    ::= { hpnicfDot11StationAssociateEntry 35 }

hpnicfDot11StationAKMModeCM OBJECT-TYPE
    SYNTAX      INTEGER
        {
            none(0),
            psk(1),
            radius(2),
            wlanex(3)
        }
    MAX-ACCESS  read-only
    STATUS      current
    DESCRIPTION
        "Represents the key management mode defined by 802.11i.
        The following values are supported:
        none         - no key management mode configured,
        psk          - pre-shared key authentication,
        radius       - 802.1x authentication,
        wlanex       - wlanex."
    ::= { hpnicfDot11StationAssociateEntry 36 }

hpnicfDot11StationSecurityCiphersCM OBJECT-TYPE
    SYNTAX      INTEGER
        {
            none(0),
            wep40(1),
            wep104(2),
            tkip(3),
            aesccmp(4),
            wpisms4(5)
        }
    MAX-ACCESS  read-only
    STATUS      current
    DESCRIPTION
        "Represents the frame encryption cipher type used by
        station.
        The following values are supported:
        none     - clear text or no cipher method is configure,
        wep40    - 40-bit WEP key,
        wep104   - 104-bit WEP key,
        tkip     - WPA Temporal Key encryption,
        aesccmp  - WPA AES CCMP encryption,
        wpisms4  - ext encryption."
    ::= { hpnicfDot11StationAssociateEntry 37 }

hpnicfDot11StationSecIEStatusCM OBJECT-TYPE
    SYNTAX      INTEGER
        {
            none(0),
            wpa(1),
            wpa2(2),
            wlanex(3)
        }
    MAX-ACCESS  read-only
    STATUS      current
    DESCRIPTION
        "Represents the security Information element for this station.
        The following values are supported:
        none    - both wpa and wpa2 are disabled,
        wpa     - only enable wpa,
        wpa2    - only enable wpa2,
        wlanex  - only enable wlanex."
    ::= { hpnicfDot11StationAssociateEntry 38 }

hpnicfDot11StationIPv6Address OBJECT-TYPE
    SYNTAX      OCTET STRING
    MAX-ACCESS  read-only
    STATUS      current
    DESCRIPTION
        "Represents the IPv6 address of the station."
    ::= { hpnicfDot11StationAssociateEntry 39 }

-- *****************************************************************************
-- *  End of hpnicfDot11StaAssociateTable Definition
-- *****************************************************************************

-- *****************************************************************************
-- *  hpnicfDot11StationAPRelationTable Definition
-- *****************************************************************************
hpnicfDot11StationAPRelationTable OBJECT-TYPE
    SYNTAX      SEQUENCE OF HpnicfDot11StationAPRelationEntry
    MAX-ACCESS  not-accessible
    STATUS      current
    DESCRIPTION
        "This table contains relation-ship between station, AP, Radio
        and WLANID, and the detailed information of station is kept in
        the hpnicfDot11StaAssociateTable table."
    ::= { hpnicfDot11StationMtGroup 2 }

hpnicfDot11StationAPRelationEntry OBJECT-TYPE
    SYNTAX      HpnicfDot11StationAPRelationEntry
    MAX-ACCESS  not-accessible
    STATUS      current
    DESCRIPTION
        "Each entry contains relation-ship information
        with AP, Radio and WLANID of each station."
    INDEX
        {
            hpnicfDot11StationMAC
        }
    ::= { hpnicfDot11StationAPRelationTable 1 }

HpnicfDot11StationAPRelationEntry ::= SEQUENCE
    {
        hpnicfDot11CurrAPID       HpnicfDot11ObjectIDType,
        hpnicfDot11CurrRadioID    HpnicfDot11RadioScopeType,
        hpnicfDot11CurrWlanID     Integer32,
        hpnicfDot11CurrAntennaID  Integer32
    }

hpnicfDot11CurrAPID OBJECT-TYPE
    SYNTAX      HpnicfDot11ObjectIDType
    MAX-ACCESS  read-only
    STATUS      current
    DESCRIPTION
        "To uniquely identify each AP, and relation-ship
        between hpnicfDot11CurrAPID and AP device will be static."
    ::= { hpnicfDot11StationAPRelationEntry 1 }

hpnicfDot11CurrRadioID OBJECT-TYPE
    SYNTAX      HpnicfDot11RadioScopeType
    MAX-ACCESS  read-only
    STATUS      current
    DESCRIPTION
        "Represents each radio."
    ::= { hpnicfDot11StationAPRelationEntry 2 }

hpnicfDot11CurrWlanID OBJECT-TYPE
    SYNTAX      Integer32
    MAX-ACCESS  read-only
    STATUS      current
    DESCRIPTION
        "Represents WLAN ID of the BSS the station associated to."
    ::= { hpnicfDot11StationAPRelationEntry 3 }

hpnicfDot11CurrAntennaID OBJECT-TYPE
    SYNTAX      Integer32
    MAX-ACCESS  read-only
    STATUS      current
    DESCRIPTION
        "Represents Antenna ID of the station associated to."
    ::= { hpnicfDot11StationAPRelationEntry 4 }
-- *****************************************************************************
-- *  End of hpnicfDot11StationAPRelationTable Definition
-- *****************************************************************************

-- *****************************************************************************
-- *  hpnicfDot11StationStatisTable Definition
-- *****************************************************************************
hpnicfDot11StationStatisTable OBJECT-TYPE
    SYNTAX      SEQUENCE OF HpnicfDot11StationStatisEntry
    MAX-ACCESS  not-accessible
    STATUS      current
    DESCRIPTION
        "This table contains statistics and status of all
        stations in the hpnicfDot11StaAssociateTable."
    ::= { hpnicfDot11StationMtGroup 3 }

hpnicfDot11StationStatisEntry OBJECT-TYPE
    SYNTAX      HpnicfDot11StationStatisEntry
    MAX-ACCESS  not-accessible
    STATUS      current
    DESCRIPTION
        "This entry contains statistics and status for each station."
    INDEX
        {
            hpnicfDot11StationMAC
        }
    ::= { hpnicfDot11StationStatisTable 1 }

HpnicfDot11StationStatisEntry ::= SEQUENCE
    {
        hpnicfDot11StationRxFrameCnt        Counter32,
        hpnicfDot11StationTxFrameCnt        Counter32,
        hpnicfDot11StationDropFrameCnt      Counter32,
        hpnicfDot11StationRxFrameBytes      Counter64,
        hpnicfDot11StationTxFrameBytes      Counter64,
        hpnicfDot11StationDropFrameBytes    Counter64,
        hpnicfDot11StationRxRetryPkts       Counter32,
        hpnicfDot11StationTxRetryPkts       Counter32,
        hpnicfDot11StationRxRetryBytes      Counter64,
        hpnicfDot11StationTxRetryBytes      Counter64,
        hpnicfDot11StationThroughput        Counter64,
        hpnicfDot11StationSuccessTxCnt      Counter32,
        hpnicfDot11StationSuccessTxDataCnt  Counter32,
        hpnicfDot11StationRxDataFrameCnt    Counter32,
        hpnicfDot11StationTxDataFrameCnt    Counter32,
        hpnicfDot11StationRxDataFrameBytes  Counter64,
        hpnicfDot11StationTxDataFrameBytes  Counter64,
        hpnicfDot11StationRxFragCnt         Counter32,
        hpnicfDot11StaRxErrDataFrameCnt     Counter64,
        hpnicfDot11StaTxRetryDataFrameCnt   Counter64,
        hpnicfDot11StaTxDataRatePkts        OCTET STRING,
        hpnicfDot11StaRxDataRatePkts        OCTET STRING,
        hpnicfDot11StaTxSignalStrengthPkts  OCTET STRING,
        hpnicfDot11StaInternetRxFrameBytes  Counter64,
        hpnicfDot11StaInternetTxFrameBytes  Counter64,
        hpnicfDot11StaLocalRxFrameBytes     Counter64,
        hpnicfDot11StaLocalTxFrameBytes     Counter64
    }

hpnicfDot11StationRxFrameCnt OBJECT-TYPE
    SYNTAX      Counter32
    MAX-ACCESS  read-only
    STATUS      current
    DESCRIPTION
        "Represents the count of frames that are received by AP from station."
    ::= { hpnicfDot11StationStatisEntry 1 }

hpnicfDot11StationTxFrameCnt OBJECT-TYPE
    SYNTAX      Counter32
    MAX-ACCESS  read-only
    STATUS      current
    DESCRIPTION
        "Represents the count of frames that are sent to station from AP."
    ::= { hpnicfDot11StationStatisEntry 2 }

hpnicfDot11StationDropFrameCnt OBJECT-TYPE
    SYNTAX      Counter32
    MAX-ACCESS  read-only
    STATUS      current
    DESCRIPTION
        "Represents the count of frames that are dropped."
    ::= { hpnicfDot11StationStatisEntry 3 }

hpnicfDot11StationRxFrameBytes OBJECT-TYPE
    SYNTAX      Counter64
    UNITS       "bytes"
    MAX-ACCESS  read-only
    STATUS      current
    DESCRIPTION
        "Represents the count of bytes that are received by AP from station."
    ::= { hpnicfDot11StationStatisEntry 4 }

hpnicfDot11StationTxFrameBytes OBJECT-TYPE
    SYNTAX      Counter64
    UNITS       "bytes"
    MAX-ACCESS  read-only
    STATUS      current
    DESCRIPTION
        "Represents the count of bytes that are sent to station from AP."
    ::= { hpnicfDot11StationStatisEntry 5 }

hpnicfDot11StationDropFrameBytes OBJECT-TYPE
    SYNTAX      Counter64
    UNITS       "bytes"
    MAX-ACCESS  read-only
    STATUS      current
    DESCRIPTION
        "Represents how many bytes are dropped."
    ::= { hpnicfDot11StationStatisEntry 6 }

hpnicfDot11StationRxRetryPkts OBJECT-TYPE
    SYNTAX      Counter32
    MAX-ACCESS  read-only
    STATUS      current
    DESCRIPTION
        "Represents the count of frames that are retransmitted to AP from station."
    ::= { hpnicfDot11StationStatisEntry 7 }

hpnicfDot11StationTxRetryPkts OBJECT-TYPE
    SYNTAX      Counter32
    MAX-ACCESS  read-only
    STATUS      current
    DESCRIPTION
        "Represents the count of frames that are retransmitted to station from AP."
    ::= { hpnicfDot11StationStatisEntry 8 }

hpnicfDot11StationRxRetryBytes OBJECT-TYPE
    SYNTAX      Counter64
    MAX-ACCESS  read-only
    STATUS      current
    DESCRIPTION
        "Represents the count of bytes that are retransmitted to AP from station."
    ::= { hpnicfDot11StationStatisEntry 9 }

hpnicfDot11StationTxRetryBytes OBJECT-TYPE
    SYNTAX      Counter64
    MAX-ACCESS  read-only
    STATUS      current
    DESCRIPTION
        "Represents the count of bytes that are retransmitted to station from AP."
    ::= { hpnicfDot11StationStatisEntry 10 }

hpnicfDot11StationThroughput OBJECT-TYPE
    SYNTAX      Counter64
    UNITS       "bytes"
    MAX-ACCESS  read-only
    STATUS      current
    DESCRIPTION
        "Represents how many payload bytes of data frame are sent and received
         by station."
    ::= { hpnicfDot11StationStatisEntry 11 }

hpnicfDot11StationSuccessTxCnt OBJECT-TYPE
    SYNTAX      Counter32
    MAX-ACCESS  read-only
    STATUS      current
    DESCRIPTION
        "Represents how many frames have been successfully sent to station."
    ::= { hpnicfDot11StationStatisEntry 12 }

hpnicfDot11StationSuccessTxDataCnt  OBJECT-TYPE
    SYNTAX      Counter32
    MAX-ACCESS  read-only
    STATUS      current
    DESCRIPTION
        "Represents how many data frames have been successfully sent to
        station."
    ::= { hpnicfDot11StationStatisEntry 13 }

hpnicfDot11StationRxDataFrameCnt OBJECT-TYPE
    SYNTAX      Counter32
    MAX-ACCESS  read-only
    STATUS      current
    DESCRIPTION
        "Represents how many data frames have been received from station."
    ::= { hpnicfDot11StationStatisEntry 14 }

hpnicfDot11StationTxDataFrameCnt OBJECT-TYPE
    SYNTAX      Counter32
    MAX-ACCESS  read-only
    STATUS      current
    DESCRIPTION
        "Represents how many data frames have been sent to station."
    ::= { hpnicfDot11StationStatisEntry 15 }

hpnicfDot11StationRxDataFrameBytes OBJECT-TYPE
    SYNTAX      Counter64
    MAX-ACCESS  read-only
    STATUS      current
    DESCRIPTION
        "Represents how many bytes of data frames have been received
        from station."
    ::= { hpnicfDot11StationStatisEntry 16 }

hpnicfDot11StationTxDataFrameBytes OBJECT-TYPE
    SYNTAX      Counter64
    MAX-ACCESS  read-only
    STATUS      current
    DESCRIPTION
        "Represents how many bytes of data frames have been sent to
        station."
    ::= { hpnicfDot11StationStatisEntry 17 }

hpnicfDot11StationRxFragCnt  OBJECT-TYPE
    SYNTAX      Counter32
    MAX-ACCESS  read-only
    STATUS      current
    DESCRIPTION
        "Represents the number of fragmented data frames that received
         from station."
    ::= { hpnicfDot11StationStatisEntry 18 }

hpnicfDot11StaRxErrDataFrameCnt  OBJECT-TYPE
        SYNTAX      Counter64
        MAX-ACCESS  read-only
        STATUS      current
        DESCRIPTION
                "Represents the count of error data frames that are received by AP
                 from station."
    ::= { hpnicfDot11StationStatisEntry 19 }

hpnicfDot11StaTxRetryDataFrameCnt  OBJECT-TYPE
        SYNTAX      Counter64
        MAX-ACCESS  read-only
        STATUS      current
        DESCRIPTION
                "Represents the count of data frames that are retransmitted to station
                 from AP."
    ::= { hpnicfDot11StationStatisEntry 20 }
hpnicfDot11StaTxDataRatePkts  OBJECT-TYPE
        SYNTAX      OCTET STRING
        MAX-ACCESS  read-only
        STATUS      current
        DESCRIPTION
                "Represents how many data frames of each rate have been received
                from station."
    ::= { hpnicfDot11StationStatisEntry 21 }

hpnicfDot11StaRxDataRatePkts  OBJECT-TYPE
        SYNTAX      OCTET STRING
        MAX-ACCESS  read-only
        STATUS      current
        DESCRIPTION
                "Represents how many data frames of each rate have been sent to
                station."
    ::= { hpnicfDot11StationStatisEntry 22 }

hpnicfDot11StaTxSignalStrengthPkts  OBJECT-TYPE
        SYNTAX      OCTET STRING
        MAX-ACCESS  read-only
        STATUS      current
        DESCRIPTION
                "Represents how many data frames of different signal strength have been
                 received from station."
    ::= { hpnicfDot11StationStatisEntry 23 }

hpnicfDot11StaInternetRxFrameBytes OBJECT-TYPE
    SYNTAX      Counter64
    MAX-ACCESS  read-only
    STATUS      current
    DESCRIPTION
        "Internet traffic bytes received from station."
    ::= { hpnicfDot11StationStatisEntry 24 }

hpnicfDot11StaInternetTxFrameBytes OBJECT-TYPE
    SYNTAX      Counter64
    MAX-ACCESS  read-only
    STATUS      current
    DESCRIPTION
        "Internet traffic bytes sent to station."
    ::= { hpnicfDot11StationStatisEntry 25 }

hpnicfDot11StaLocalRxFrameBytes OBJECT-TYPE
    SYNTAX      Counter64
    MAX-ACCESS  read-only
    STATUS      current
    DESCRIPTION
        "Local traffic bytes received from station."
    ::= { hpnicfDot11StationStatisEntry 26 }

hpnicfDot11StaLocalTxFrameBytes OBJECT-TYPE
    SYNTAX      Counter64
    MAX-ACCESS  read-only
    STATUS      current
    DESCRIPTION
        "Local traffic bytes sent to station."
    ::= { hpnicfDot11StationStatisEntry 27 }
-- *****************************************************************************
-- *  End of hpnicfDot11StationStatisTable Definition
-- *****************************************************************************

-- *****************************************************************************
-- *  hpnicfDot11StationRfPingTable Definition
-- *****************************************************************************
hpnicfDot11StationRfPingTable OBJECT-TYPE
    SYNTAX      SEQUENCE OF HpnicfDot11StationRfPingEntry
    MAX-ACCESS  not-accessible
    STATUS      current
    DESCRIPTION
        "This table contains statistics of all
        stations in the hpnicfDot11StationRfPingTable."
    ::= { hpnicfDot11StationMtGroup 4 }

hpnicfDot11StationRfPingEntry OBJECT-TYPE
    SYNTAX      HpnicfDot11StationRfPingEntry
    MAX-ACCESS  not-accessible
    STATUS      current
    DESCRIPTION
        "This entry contains statistics for each station's RfPing results."
    INDEX
        {
            hpnicfDot11StationMAC,
            hpnicfDot11StationRfPingIndex
        }
    ::= { hpnicfDot11StationRfPingTable 1 }
HpnicfDot11StationRfPingEntry ::= SEQUENCE
    {
        hpnicfDot11StationRfPingIndex       Integer32,
        hpnicfDot11StationRfPingRate        OCTET STRING,
        hpnicfDot11StationRfPingTxCnt       Integer32,
        hpnicfDot11StationRfPingRxCnt       Integer32,
        hpnicfDot11StationRfPingRssi        Integer32,
        hpnicfDot11StationRfPingRetries     Integer32,
        hpnicfDot11StationRfPingRtt         Integer32
    }

hpnicfDot11StationRfPingIndex OBJECT-TYPE
    SYNTAX      Integer32(0..214783647)
    MAX-ACCESS  not-accessible
    STATUS      current
    DESCRIPTION
        "Represents the rate index for the station."
    ::= { hpnicfDot11StationRfPingEntry 1 }

hpnicfDot11StationRfPingRate OBJECT-TYPE
    SYNTAX      OCTET STRING
    UNITS       "Mbps"
    MAX-ACCESS  read-only
    STATUS      current
    DESCRIPTION
        "Represents the rate at which the radio interface sends wireless ping frames."
    ::= { hpnicfDot11StationRfPingEntry 2 }

hpnicfDot11StationRfPingTxCnt OBJECT-TYPE
    SYNTAX      Integer32
    MAX-ACCESS  read-only
    STATUS      current
    DESCRIPTION
        "Represents the number of wireless ping frames that the radio interface sent."
    ::= { hpnicfDot11StationRfPingEntry 3 }

hpnicfDot11StationRfPingRxCnt OBJECT-TYPE
    SYNTAX      Integer32
    MAX-ACCESS  read-only
    STATUS      current
    DESCRIPTION
        "Represents the number of wireless ping frames that
         the radio interface received from the client."
    ::= { hpnicfDot11StationRfPingEntry 4 }

hpnicfDot11StationRfPingRssi OBJECT-TYPE
    SYNTAX      Integer32
    MAX-ACCESS  read-only
    STATUS      current
    DESCRIPTION
        "Represents the client signal strength detected by the AP."
    ::= { hpnicfDot11StationRfPingEntry 5 }

hpnicfDot11StationRfPingRetries OBJECT-TYPE
    SYNTAX      Integer32
    MAX-ACCESS  read-only
    STATUS      current
    DESCRIPTION
        "Represents the total number of retransmitted ping frames."
    ::= { hpnicfDot11StationRfPingEntry 6 }

hpnicfDot11StationRfPingRtt OBJECT-TYPE
    SYNTAX      Integer32
    UNITS       "ms"
    MAX-ACCESS  read-only
    STATUS      current
    DESCRIPTION
        "Round-trip time (RTT) from the time when the radio interface send a
         ping packet to the time when it receives a response from the client."
    ::= { hpnicfDot11StationRfPingEntry 7 }
-- *****************************************************************************
-- *  End of hpnicfDot11StationRfPingTable Definition
-- *****************************************************************************

-- *****************************************************************************
-- *     Notifications OF hpnicfDot11StationNotifyGroup
-- *****************************************************************************
-- 802.11 MAC Notification

hpnicfDot11StationTraps OBJECT IDENTIFIER    ::= { hpnicfDot11StationNotifyGroup 0 }

hpnicfDot11StationMICErrorTrap NOTIFICATION-TYPE
    OBJECTS
        {
            hpnicfDot11CurrAPID,
            hpnicfDot11CurrRadioID,
            hpnicfDot11StationTrapBSSID,
            hpnicfDot11StationSSIDName,
            hpnicfDot11StationTrapStaMAC
        }
    STATUS      current
    DESCRIPTION
        "This notification is to indicate the occurrence of a MIC
        failure in a certain station."
    ::= { hpnicfDot11StationTraps 1 }

hpnicfDot11StationAuthenErrorTrap NOTIFICATION-TYPE
    OBJECTS
        {
            hpnicfDot11CurrAPID,
            hpnicfDot11CurrRadioID,
            hpnicfDot11StationTrapBSSID,
            hpnicfDot11StationSSIDName,
            hpnicfDot11StationTrapStaMAC,
            hpnicfDot11StationAuthenMode,
            hpnicfDot11StationAKMMode
        }
    STATUS      current
    DESCRIPTION
        "This notification is to indicate which station happened
        authentication failure."
    ::= { hpnicfDot11StationTraps 2 }

hpnicfDot11StationAuthorFailTrap NOTIFICATION-TYPE
    OBJECTS
        {
            hpnicfDot11StationUserName,
            hpnicfDot11StationTrapStaMAC,
            hpnicfDot11CurrRadioID,
            hpnicfDot11StationSSIDName,
            hpnicfDot11StationAuthorFailCause,
            hpnicfDot11StationFailCauseDesc,
            hpnicfDot11CurrAPID,
            hpnicfDot11StationBSSID,
            hpnicfDot11StationAuthMode,
            hpnicfDot11StationTrapAPMacAddress
        }
    STATUS      current
    DESCRIPTION
        "This trap is sent if a station authorization fails."
    ::= { hpnicfDot11StationTraps 3 }

hpnicfDot11StationAssocFailTrap NOTIFICATION-TYPE
    OBJECTS
        {
            hpnicfDot11StationTrapStaMAC,
            hpnicfDot11CurrRadioID,
            hpnicfDot11StationSSIDName,
            hpnicfDot11StationAssocFailCause,
            hpnicfDot11StationFailCauseDesc,
            hpnicfDot11CurrAPID,
            hpnicfDot11StationTrapAPMacAddress
        }
    STATUS      current
    DESCRIPTION
        "This trap is sent if a station association fails."
    ::= { hpnicfDot11StationTraps 4 }

hpnicfDot11StationDeAssocTrap NOTIFICATION-TYPE
    OBJECTS
        {
            hpnicfDot11StationUserName,
            hpnicfDot11StationTrapStaMAC,
            hpnicfDot11StationVlanId,
            hpnicfDot11CurrRadioID,
            hpnicfDot11StationSSIDName,
            hpnicfDot11StationSessionDuration,
            hpnicfDot11CurrAPID,
            hpnicfDot11StationAPName,
            hpnicfDot11StationBSSID
        }
    STATUS      current
    DESCRIPTION
        "This trap is sent if a station de-association occurred."
    ::= { hpnicfDot11StationTraps 5 }

hpnicfDot11StationAuthorSuccTrap NOTIFICATION-TYPE
    OBJECTS
        {
            hpnicfDot11StationUserName,
            hpnicfDot11StationTrapStaMAC,
            hpnicfDot11StationVlanId,
            hpnicfDot11StationSessionStartTime,
            hpnicfDot11CurrRadioID,
            hpnicfDot11StationSSIDName,
            hpnicfDot11CurrAPID,
            hpnicfDot11StationAPName,
            hpnicfDot11StationBSSID
        }
    STATUS      current
    DESCRIPTION
        "This trap is sent when a station is authorized successfully."
    ::= { hpnicfDot11StationTraps 6 }

hpnicfDot11StationRoamingTrap NOTIFICATION-TYPE
    OBJECTS
        {
            hpnicfDot11CurrAPID,
            hpnicfDot11StationUserName,
            hpnicfDot11StationTrapStaMAC,
            hpnicfDot11StationVlanId,
            hpnicfDot11StationRoamingTime,
            hpnicfDot11CurrRadioID,
            hpnicfDot11StationSSIDName,
            hpnicfDot11StationACIPAddress,
            hpnicfDot11StationACIPv6Add
        }
    STATUS      current
    DESCRIPTION
        "This trap is sent when a station roamed successfully."
    ::= { hpnicfDot11StationTraps 7 }

hpnicfDot11StationDisconnectTrap NOTIFICATION-TYPE
    OBJECTS
        {
            hpnicfDot11StationAPName,
            hpnicfDot11StationBSSID,
            hpnicfDot11StationSSIDName,
            hpnicfDot11StationSessionDuration,
            hpnicfDot11StationVlanId,
            hpnicfDot11CurrAPID,
            hpnicfDot11CurrRadioID,
            hpnicfDot11StaDisconnectReason,
            hpnicfDot11StationTrapStaMAC
        }
    STATUS      current
    DESCRIPTION
        "This notification is sent when station disconnects with AP."
    ::= { hpnicfDot11StationTraps 8 }

hpnicfDot11UserDisconnectTrap NOTIFICATION-TYPE
    OBJECTS
        {
            hpnicfDot11StationAPName,
            hpnicfDot11StationTrapStaMAC,
            hpnicfDot11UserName
        }
    STATUS      current
    DESCRIPTION
        "This notification is sent when user disconnects with AP."
    ::= { hpnicfDot11StationTraps 9 }

hpnicfDot11StaAntennaChgTrap NOTIFICATION-TYPE
    OBJECTS
        {
            hpnicfDot11CurrAPID,
            hpnicfDot11CurrRadioID,
            hpnicfDot11StationTrapBSSID,
            hpnicfDot11StationSSIDName,
            hpnicfDot11StationTrapStaMAC,
            hpnicfDot11StationTrapOldAntennaID,
            hpnicfDot11StationTrapNewAntennaID
        }
    STATUS      current
    DESCRIPTION
        "This notification is to indicate the station has connected to a new antenna."
    ::= { hpnicfDot11StationTraps 10 }

-- 802.11 station Notify variable object

        hpnicfDot11StationTrapVarObjects OBJECT IDENTIFIER
    ::= { hpnicfDot11StationNotifyGroup 1 }

hpnicfDot11StationTrapBSSID OBJECT-TYPE
    SYNTAX      MacAddress
    MAX-ACCESS  accessible-for-notify
    STATUS      current
    DESCRIPTION
        "Represents on which BSSID of AP the event happened."
    ::= { hpnicfDot11StationTrapVarObjects 1 }

hpnicfDot11StationTrapStaMAC OBJECT-TYPE
    SYNTAX      MacAddress
    MAX-ACCESS  accessible-for-notify
    STATUS      current
    DESCRIPTION
        "Represents the MAC address of station which happened message
        integrity check (MIC) errors."
    ::= { hpnicfDot11StationTrapVarObjects 2 }

hpnicfDot11StationSessionStartTime OBJECT-TYPE
    SYNTAX      DateAndTime
    MAX-ACCESS  accessible-for-notify
    STATUS      current
    DESCRIPTION
        "Represents the time at which the station connected."
    ::= { hpnicfDot11StationTrapVarObjects 3 }

hpnicfDot11StationAssocFailCause OBJECT-TYPE
    SYNTAX      HpnicfDot11AssocFailType
    MAX-ACCESS  accessible-for-notify
    STATUS      current
    DESCRIPTION
        "Represents the cause of the station association failure."
    ::= { hpnicfDot11StationTrapVarObjects 4 }

hpnicfDot11StationAuthorFailCause OBJECT-TYPE
    SYNTAX      HpnicfDot11AuthorFailType
    MAX-ACCESS  accessible-for-notify
    STATUS      current
    DESCRIPTION
        "Represents the cause of the station authorization failure."
    ::= { hpnicfDot11StationTrapVarObjects 5 }

hpnicfDot11StationFailCauseDesc OBJECT-TYPE
    SYNTAX      OCTET STRING(SIZE(0..255))
    MAX-ACCESS  accessible-for-notify
    STATUS      current
    DESCRIPTION
        "Represents the failure description of the station."
    ::= { hpnicfDot11StationTrapVarObjects 6 }

hpnicfDot11StationSessionDuration OBJECT-TYPE
    SYNTAX      Unsigned32
    UNITS       "second"
    MAX-ACCESS  accessible-for-notify
    STATUS      current
    DESCRIPTION
        "Represents the duration of the station sesssion."
    ::= { hpnicfDot11StationTrapVarObjects 7 }

hpnicfDot11StationRoamingTime OBJECT-TYPE
    SYNTAX      Unsigned32
    UNITS       "second"
    MAX-ACCESS  accessible-for-notify
    STATUS      current
    DESCRIPTION
        "Represents the time at which the station roamed."
    ::= { hpnicfDot11StationTrapVarObjects 8 }

hpnicfDot11StationACIPAddress OBJECT-TYPE
    SYNTAX      IpAddress
    MAX-ACCESS  accessible-for-notify
    STATUS      current
    DESCRIPTION
        "For roam-in station, it represents the ip address of home AC.
         For roam-out station, it represents the ip address of foreign AC."
    ::= { hpnicfDot11StationTrapVarObjects 9 }

hpnicfDot11StationAPName OBJECT-TYPE
    SYNTAX      OCTET STRING
    MAX-ACCESS  accessible-for-notify
    STATUS      current
    DESCRIPTION
        "Name of the AP which the station connects to."
    ::= { hpnicfDot11StationTrapVarObjects 10 }

hpnicfDot11StationBSSID OBJECT-TYPE
    SYNTAX      MacAddress
    MAX-ACCESS  accessible-for-notify
    STATUS      current
    DESCRIPTION
        "BSSID which the station connects to."
    ::= { hpnicfDot11StationTrapVarObjects 11 }

hpnicfDot11StaDisconnectReason OBJECT-TYPE
    SYNTAX      OCTET STRING
    MAX-ACCESS  accessible-for-notify
    STATUS      current
    DESCRIPTION
        "Reason why the station disconnects with the AP."
    ::= { hpnicfDot11StationTrapVarObjects 12 }

hpnicfDot11StationAuthMode OBJECT-TYPE
    SYNTAX      INTEGER
    {
        opensystem(1),
        sharedkey(2)
    }
    MAX-ACCESS  accessible-for-notify
    STATUS      current
    DESCRIPTION
        "Represents station's authentication mode."
    ::= { hpnicfDot11StationTrapVarObjects 13 }

hpnicfDot11StationACIPv6Add OBJECT-TYPE
    SYNTAX      OCTET STRING
    MAX-ACCESS  accessible-for-notify
    STATUS      current
    DESCRIPTION
        "For roam-in station, it represents the IPv6 address of home AC.
         For roam-out station, it represents the IPv6 address of foreign AC."
    ::= { hpnicfDot11StationTrapVarObjects 14 }

hpnicfDot11UserName OBJECT-TYPE
    SYNTAX      OCTET STRING
    MAX-ACCESS  accessible-for-notify
    STATUS      current
    DESCRIPTION
        "Represents the user name."
    ::= { hpnicfDot11StationTrapVarObjects 15 }

hpnicfDot11StationTrapAPMacAddress OBJECT-TYPE
    SYNTAX      MacAddress
    MAX-ACCESS  accessible-for-notify
    STATUS      current
    DESCRIPTION
        "Represents the MAC address of an AP."
    ::= { hpnicfDot11StationTrapVarObjects 16 }

hpnicfDot11StationTrapOldAntennaID OBJECT-TYPE
    SYNTAX      Integer32
    MAX-ACCESS  accessible-for-notify
    STATUS      current
    DESCRIPTION
        "Represents the ID of the old antenna to which the station is associated."
    ::= { hpnicfDot11StationTrapVarObjects 17 }

hpnicfDot11StationTrapNewAntennaID OBJECT-TYPE
    SYNTAX      Integer32
    MAX-ACCESS  accessible-for-notify
    STATUS      current
    DESCRIPTION
        "Represents the ID of the new antenna to which the station is associated."
    ::= { hpnicfDot11StationTrapVarObjects 18 }

-- *****************************************************************************
-- *     End OF NotifyGroup
-- *****************************************************************************
END
