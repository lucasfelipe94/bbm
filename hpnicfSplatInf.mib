-- ==================================================================
-- Copyright (c) 2010-2016 Hewlett-Packard Development Company, L.P.
--
-- Description: Interface Management MIB
-- Reference:
-- Version: V3.7
-- History:
--      V1.0 (1) Created by Zhangshilin, 2001.06.29
--           (2) Revised by Qizhenglin, 2002.01.08
--      V1.1 2004/7/20 Add PortList and VlanIndex define
--      V1.2 2004/8/05 Add hpnicfifEthernetIsolate and hpnicfIsolateGroupMax
--                     by Chenshixing
--      V1.3 2004/9/08 add fabric value to hpnicfifVLANType object and
--                     change the DESCRIPTION by chenshixing
--           2004/9/08 1.change the DESCRIPTION and the range of
--                       SYNTAX  INTEGER  from (5..100) to (1..100)
--                       in hpnicfifMcastControl object by wangyingxia
--                     2.add the hpnicfifPpsMcastControl object
--                       by wangyingxia
--                     3.change the status  in hpnicfLswVlanMngObject
--                       to current by gaolong
--      V1.4 2004-10-12 updated by gaolong
--           Import TEXTUAL-CONVENTION, OBJECT-IDENTITY, Unsigned32.
--           Relocate hpnicfLswL2InfMib MODULE-IDENTITY clause.
--           Change SYNTAX clause type of VlanIndex from INTEGER to Unsigned32.
--           Change MAX-ACCESS clause vlaue of hpnicfifClearStat and hpnicfifEthernetTest
--           from write-only to read-write.
--           Change value of hpnicfifAggregateModel, hpnicfdot1qVlanType, hpnicfVlanInterfaceFrameType
--           and hpnicfifEthernetMdi from underscores to hyphens.
--           Change value of hpnicfifMacAddrLearnMode, beginning with lowercase.
--      V1.5 2004-11-15
--           Add the object hpnicfdot1qVlanBcastSuppressionPPS by lihaijun
--           Adjust the format of the description of hpnicfdot1qVlanBroadcastSuppression
--      V1.6 2004-12-2
--           Add the object hpnicfGlobalBroadcastMaxPps by zhanggang
--           Add the object hpnicfGlobalBroadcastMaxRatio by zhanggang
--           Add hpnicfifVlanVPNStatus and hpnicfBpduTunnelStatus by caiqiang
--           Add hpnicfVlanInterfaceIpMethod by wangchao
--      V1.7 2005-01-22
--           Remove the content of hpnicfLswVlan from this MIB to HPN-ICF-LswVLAN-MIB
--           Remove SnmpAdminString
--      V1.8 2005-2-2
--           Add the object hpnicfifPpsBcastDisValControl by zhangjianwei
--      V1.9 2005-03-08
--           Add hpnicfifUniSuppressionStep, hpnicfifPpsUniSuppressionMax, hpnicfifMulSuppressionStep,
--           hpnicfifPpsMulSuppressionMax, hpnicfifUniSuppression, hpnicfifPpsUniSuppression,
--           hpnicfifMulSuppression, hpnicfifPpsMulSuppression by wanghaisheng
--      V2.0 2005-06-14
--           Add the object hpnicfifComboActivePort by majun and adjust format
--      V2.1 2005-06-30
--           Add the object hpnicfifVlanVPNUplinkStatus, hpnicfifVlanVPNTPID,
--           hpnicfVlanVPNTPIDMode and hpnicfVlanVPNTPID by hejunwei
--           Add hpnicfifUnknownPacketDropMul, hpnicfifUnknownPacketDropUni by wangyupeng
--           Add hpnicfifBMbpsMulSuppressionMax, hpnicfifBMbpsMulSuppression,
--           hpnicfifBKbpsMulSuppressionMax, hpnicfifBKbpsMulSuppressionStep
--           and hpnicfifBKbpsMulSuppression by lichunyan
--           Update decription of MIB objects by gaolong
--      V2.2 2005-09-05
--           Add the object hpnicfifIsolateGroupID, hpnicfifisUplinkPort,
--           hpnicfPortIsolateGroupTable, hpnicfPortIsolateGroupEntry,
--           hpnicfPortIsolateGroupIndex, hpnicfPortIsolateUplinkIfIndex,
--           hpnicfPortIsolateGroupRowStatus by huzinan
--      V2.3 2005-10-13
--           Add the object hpnicfPortIsolateGroupDescription by hejunwei
--      V2.4 2005-11-15
--           Add the value 24000M to hpnicfifEthernetSpeed by wanglirong
--      V2.5 2006-01-16
--           Add hpnicfMaxMacLearnRange by zhangyinfei
--           Change the DESCRIPTION and the range of hpnicfMaxMacLearn by zhangyinfei
--      V2.6 2006-01-03
--           Remove the value range from the definition of hpnicfifXXBasePortIndex
--           by wangzhaoyan
--      V2.7 2006-02-11
--           Modify description of hpnicfifXXBasePortIndex and hpnicfifXXDevPortIndex
--           Modify description of hpnicfifHybridTaggedVlanListLow, hpnicfifHybridTaggedVlanListHigh,
--           hpnicfifHybridUnTaggedVlanListLow and hpnicfifHybridUnTaggedVlanListHigh
--           Modify some wrong format of the description
--      V2.8 2006-03-14
--           Add hpnicfifEthernetAutoSpeedMask, hpnicfifEthernetAutoSpeed in
--           hpnicfethernetTable and SpeedModeFlag definition by Jin Yongfeng.
--      V2.9 2006-04-24
--           Remove value range of hpnicfifEthernetMTU by Chenxi.
--      V3.0 2006-04-30
--           Add hpnicfifBMbpsUniSuppressionMax, hpnicfifBMbpsUniSuppression,
--           hpnicfifBKbpsUniSuppressionMax, hpnicfifBKbpsUniSuppressionStep
--           and hpnicfifBKbpsUniSuppression by lichunyan.
--      V3.1 2006-09-27
--           hpnicfifComboActivePort is obsoleted in hpnicfifXXTable.
--           hpnicfifComboPortTable is added for combo interface.
--           hpnicfifComboActivePort is replaced with hpnicfifComboPortCurActive.
--      V3.2 2009-04-11
--           Add hpnicfifOutPayloadOctets, hpnicfifInPayloadOctets, hpnicfifInErrorPktsRate,
--           hpnicfifInPkts, hpnicfifInNormalPkts, hpnicfifOutPkts by lisong.
--      V3.3 2011-11-08
--           Add the value s40000M and s100000M to SpeedModeFlag and
--           hpnicfifEthernetSpeed by xiedong.
--      V3.4 2012-09-29
--           Modify description of hpnicfifClearStat by xiedong.
--           2012-11-03
--           Add hpnicfifPktBufTable, hpnicfifPktBufEntry, hpnicfifPktBufFree,
--           hpnicfifPktBufInit, hpnicfifPktBufMin, hpnicfifPktBufMiss by chenkaiping
--      V3.5 2013-08-17
--           Add hpnicfifPortProtocolStatTable by yangxiaoren.
--      V3.6 2014-02-08
--           Modify description of hpnicfifUniSuppression, hpnicfifMulSuppression and
--           hpnicfifMcastControl, modify value list of hpnicfifMcastControl by huhonghui,
--           for supporting value 0.
--      V3.7 2015-10-14
--           Add hpnicfifMulSuppressionFlag by chenzhouhui.
--           Modify description of hpnicfifMulSuppression and hpnicfifPpsMulSuppression by chenzhouhui.
--           Add hpnicfifPktBufInDrop and hpnicfifPktBufEgDrop to hpnicfifPktBufTable,
--           add hpnicfifQueuePktBufTable by zhangji.
-- ==================================================================
--
-- Varibles and types be imported
--
-- ==================================================================
HPN-ICF-LswINF-MIB DEFINITIONS ::= BEGIN

IMPORTS
    RowStatus, DisplayString, TruthValue, TEXTUAL-CONVENTION
        FROM SNMPv2-TC
    MODULE-IDENTITY, OBJECT-TYPE, Integer32, Counter64, Unsigned32, Counter32
        FROM SNMPv2-SMI
    ifIndex, InterfaceIndex
        FROM IF-MIB
    hpnicflswCommon
        FROM HPN-ICF-OID-MIB;

    hpnicfLswL2InfMib MODULE-IDENTITY
            LAST-UPDATED "201510140000Z"
            ORGANIZATION
                ""
            CONTACT-INFO
                ""
            DESCRIPTION
            ""
            REVISION "201510140000Z"
            DESCRIPTION
                "Add hpnicfifPktBufInDrop and hpnicfifPktBufEgDrop to hpnicfifPktBufTable,
                 hpnicfifMulSuppressionFlag, and hpnicfifQueuePktBufTable, modify description of hpnicfifMulSuppression and hpnicfifPpsMulSuppression"
            REVISION "200106290000Z"
            DESCRIPTION
            "Initial version."
            ::= { hpnicflswCommon 5 }


-- =============================================================
-- Textual Conventions
-- =============================================================

    PortList ::= TEXTUAL-CONVENTION
        STATUS      current
        DESCRIPTION
            "Each octet within this value specifies a set of eight
            ports, with the first octet specifying ports 1 through
            8, the second octet specifying ports 9 through 16, etc.
            Within each octet, the most significant bit represents
            the lowest numbered port, and the least significant bit
            represents the highest numbered port.  Thus, each port
            of the bridge is represented by a single bit within the
            value of this object.  If that bit has a value of '1'
            then that port is included in the set of ports; the port
            is not included if its bit has a value of '0'."
        SYNTAX      OCTET STRING


    VlanIndex ::= TEXTUAL-CONVENTION
        STATUS      current
        DESCRIPTION
            "A value used to index per-VLAN tables: values of 0 and
            4095 are not permitted; if the value is between 1 and
            4094 inclusive, it represents an IEEE 802.1Q VLAN-ID with
            global scope within a given bridged domain (see VlanId
            textual convention).  If the value is greater than 4095
            then it represents a VLAN with scope local to the
            particular agent, i.e. one without a global VLAN-ID
            assigned to it. Such VLANs are outside the scope of
            IEEE 802.1Q but it is convenient to be able to manage them
            in the same way using this MIB."
        SYNTAX      Unsigned32 (0..4294967295)

    DropDirection ::= TEXTUAL-CONVENTION
       STATUS  current
       DESCRIPTION
          "Representing the direction of dropping packets, if applicable."
       SYNTAX  INTEGER  {
                   disable        (1),
                   enableInbound  (2),
                   enableOutbound (3),
                   enableBoth     (4)
               }

    SpeedModeFlag ::= TEXTUAL-CONVENTION
        STATUS current
        DESCRIPTION
            "Type of Negotiable Speed mode."
        SYNTAX BITS
            {
                s10M(0),       -- 10M speed
                s100M(1),      -- 100M speed
                s1000M(2),     -- 1000M speed
                s10000M(3),    -- 10000M speed
                s24000M(4),    -- 24000M speed
                s40000M(5),    -- 40000M speed
                s100000M(6)    -- 100000M speed
            }


-- ==================================================================
--
-- ======================= definition begin =========================
--
-- ==================================================================
    hpnicfLswExtInterface OBJECT IDENTIFIER ::= { hpnicflswCommon 1 }

    hpnicfifXXTable  OBJECT-TYPE
        SYNTAX SEQUENCE OF HpnicfIfXXEntry
        MAX-ACCESS not-accessible
        STATUS   current
        DESCRIPTION "Extended interface information table."
        ::= { hpnicfLswExtInterface  1 }


    hpnicfifXXEntry  OBJECT-TYPE
        SYNTAX HpnicfIfXXEntry
        MAX-ACCESS not-accessible
        STATUS   current
        DESCRIPTION "Entries of extended interface information table."
        INDEX { ifIndex }
        ::= { hpnicfifXXTable 1}

    HpnicfIfXXEntry ::=
    SEQUENCE {
        hpnicfifUnBoundPort     TruthValue  ,
        hpnicfifISPhyPort       TruthValue  ,
        hpnicfifAggregatePort   TruthValue  ,
        hpnicfifMirrorPort      TruthValue  ,
        hpnicfifVLANType        INTEGER     ,
        hpnicfifMcastControl    INTEGER     ,
        hpnicfifFlowControl     TruthValue  ,
        hpnicfifSrcMacControl   TruthValue  ,
        hpnicfifClearStat       INTEGER,
        hpnicfifXXBasePortIndex INTEGER,
        hpnicfifXXDevPortIndex  INTEGER,
        hpnicfifPpsMcastControl  Integer32,
        hpnicfifPpsBcastDisValControl INTEGER,
        hpnicfifUniSuppressionStep Integer32,
        hpnicfifPpsUniSuppressionMax Integer32,
        hpnicfifMulSuppressionStep Integer32,
        hpnicfifPpsMulSuppressionMax Integer32,
        hpnicfifUniSuppression   Integer32,
        hpnicfifPpsUniSuppression Integer32,
        hpnicfifMulSuppression    Integer32,
        hpnicfifPpsMulSuppression Integer32,
        hpnicfifComboActivePort   INTEGER,
        hpnicfifBMbpsMulSuppressionMax Integer32,
        hpnicfifBMbpsMulSuppression Integer32,
        hpnicfifBKbpsMulSuppressionMax Integer32,
        hpnicfifBKbpsMulSuppressionStep Integer32,
        hpnicfifBKbpsMulSuppression Integer32,
        hpnicfifUnknownPacketDropMul DropDirection,
        hpnicfifUnknownPacketDropUni DropDirection,
        hpnicfifBMbpsUniSuppressionMax Integer32,
        hpnicfifBMbpsUniSuppression Integer32,
        hpnicfifBKbpsUniSuppressionMax Integer32,
        hpnicfifBKbpsUniSuppressionStep Integer32,
        hpnicfifBKbpsUniSuppression Integer32,
        hpnicfifOutPayloadOctets Counter64,
        hpnicfifInPayloadOctets Counter64,
        hpnicfifInErrorPktsRate Integer32,
        hpnicfifInPkts Counter64,
        hpnicfifInNormalPkts  Counter64,
        hpnicfifOutPkts Counter64,
        hpnicfifMulSuppressionFlag  INTEGER
        }


   hpnicfifUnBoundPort  OBJECT-TYPE
        SYNTAX  TruthValue
        MAX-ACCESS read-only
        STATUS current
        DESCRIPTION
            "Whether it is the unbound port. (true indicates that the port is
            the main port of the aggregation or the port does not participate
            in the aggregation.)"
        ::= { hpnicfifXXEntry 1 }


    hpnicfifISPhyPort  OBJECT-TYPE
        SYNTAX  TruthValue
        MAX-ACCESS read-only
        STATUS current
        DESCRIPTION "Whether it is a physical interface."
        ::= { hpnicfifXXEntry 2 }


    hpnicfifAggregatePort OBJECT-TYPE
        SYNTAX  TruthValue
        MAX-ACCESS read-only
        STATUS current
        DESCRIPTION "Whether it is the aggregated port. (if the port participates
                    in the aggregation, this value is true.)"
        ::= { hpnicfifXXEntry 3 }


    hpnicfifMirrorPort  OBJECT-TYPE
        SYNTAX  TruthValue
        MAX-ACCESS read-write
        STATUS current
        DESCRIPTION "Whether it is a mirror port."
        ::= { hpnicfifXXEntry 4 }


    hpnicfifVLANType  OBJECT-TYPE
        SYNTAX  INTEGER
        {
        vLANTrunk  (1),
        access   (2),
        hybrid    (3),
        fabric   (4)
        }
        MAX-ACCESS read-write
        STATUS current
        DESCRIPTION
            "port vlan types.
            hybrid (3) port can carry multiple VLANs.
            If fabric function is supported, fabric(4) means the port is
            a fabric port."
        ::= { hpnicfifXXEntry 5 }


    hpnicfifMcastControl OBJECT-TYPE
        SYNTAX  INTEGER (0..100)
        MAX-ACCESS read-write
        STATUS current
        DESCRIPTION
            "Broadcast storm suppression with the step length of 1,
            ranging from 0 to 100 percent.
            In some products the step is 5, ranging from 0 to 100."
        ::= { hpnicfifXXEntry 6 }

    hpnicfifFlowControl  OBJECT-TYPE
        SYNTAX  TruthValue
        MAX-ACCESS read-write
        STATUS current
        DESCRIPTION "Flow control status."
        ::= { hpnicfifXXEntry 7 }


    hpnicfifSrcMacControl OBJECT-TYPE
        SYNTAX  TruthValue
        MAX-ACCESS read-only
        STATUS current
        DESCRIPTION "Whether to filter by source MAC address."
        ::= { hpnicfifXXEntry 8 }


    hpnicfifClearStat  OBJECT-TYPE
        SYNTAX  INTEGER
        {
            clear(1)
        }
        MAX-ACCESS read-write
        STATUS current
        DESCRIPTION "Clear specify port statistics.  Operation read is not supported."
        ::= { hpnicfifXXEntry 9 }

    hpnicfifXXBasePortIndex OBJECT-TYPE
        SYNTAX  INTEGER
        MAX-ACCESS read-only
        STATUS current
        DESCRIPTION "Index number of the port and the first port index of the
                    device is 1."
        ::= { hpnicfifXXEntry 10 }

    hpnicfifXXDevPortIndex OBJECT-TYPE
        SYNTAX  INTEGER
        MAX-ACCESS read-only
        STATUS current
        DESCRIPTION "Device index of the port."
        ::= { hpnicfifXXEntry 11 }

   hpnicfifPpsMcastControl OBJECT-TYPE
        SYNTAX  Integer32
        MAX-ACCESS read-write
        STATUS current
        DESCRIPTION
            "The broadcast suppression with pps(packet per second) type.
            The max value is determined by the port type and product."
        ::= { hpnicfifXXEntry 12 }

   hpnicfifPpsBcastDisValControl OBJECT-TYPE
        SYNTAX  INTEGER
        {
          enable(1),
          disable(2)
        }
        MAX-ACCESS read-write
        STATUS current
        DESCRIPTION
            "Control the port's pps(packet per second) broadcast suppression.
            When the port is enabled, its pps broadcast suppression value is the
            global disperse value, and when disabled, it doesn't suppress broadcast."
        ::= { hpnicfifXXEntry 13 }

   hpnicfifUniSuppressionStep OBJECT-TYPE
        SYNTAX  Integer32
        MAX-ACCESS read-only
        STATUS current
        DESCRIPTION "The step of unicast suppression in ratio mode."
        ::= { hpnicfifXXEntry 14 }

   hpnicfifPpsUniSuppressionMax OBJECT-TYPE
        SYNTAX  Integer32
        MAX-ACCESS read-only
        STATUS current
        DESCRIPTION "The max pps(packet per second) value of unicast suppression
                    in pps mode."
        ::= { hpnicfifXXEntry 15 }

   hpnicfifMulSuppressionStep OBJECT-TYPE
        SYNTAX  Integer32
        MAX-ACCESS read-only
        STATUS current
        DESCRIPTION "The step of multicast suppression in ratio mode."
        ::= { hpnicfifXXEntry 16 }

   hpnicfifPpsMulSuppressionMax OBJECT-TYPE
        SYNTAX  Integer32
        MAX-ACCESS read-only
        STATUS current
        DESCRIPTION "The max pps(packet per second) value of multicast suppression
                    in pps mode."
        ::= { hpnicfifXXEntry 17 }

   hpnicfifUniSuppression OBJECT-TYPE
        SYNTAX  Integer32
        MAX-ACCESS read-write
        STATUS current
        DESCRIPTION
            "The unicast suppression with the ranging from 0 to 100 percent
            in ratio mode.
            The step is determined by hpnicfifUniSuppressionStep."
        ::= { hpnicfifXXEntry 18 }

   hpnicfifPpsUniSuppression OBJECT-TYPE
        SYNTAX  Integer32
        MAX-ACCESS read-write
        STATUS current
        DESCRIPTION
            "The unicast suppression in pps(packet per second) mode.
            The max value is determined by hpnicfifPpsUniSuppressionMax."
        ::= { hpnicfifXXEntry 19 }

   hpnicfifMulSuppression OBJECT-TYPE
        SYNTAX  Integer32
        MAX-ACCESS read-write
        STATUS current
        DESCRIPTION
            "The multicast suppression with ranging from 0 to 100 percent
            in ratio mode.
            The step is determined by hpnicfifMulSuppressionStep.
            If hpnicfifMulSuppressionFlag is 2 it means only unknown
            traffic suppression."
        ::= { hpnicfifXXEntry 20 }

   hpnicfifPpsMulSuppression OBJECT-TYPE
        SYNTAX  Integer32
        MAX-ACCESS read-write
        STATUS current
        DESCRIPTION
            "The multicast suppression in pps(packet per second) mode.
            The max pps value is determined by hpnicfifPpsMulSuppressionMax.
            If hpnicfifMulSuppressionFlag is 2 it means only unknown
            traffic suppression."
        ::= { hpnicfifXXEntry 21 }

   hpnicfifComboActivePort OBJECT-TYPE
        SYNTAX  INTEGER
        {
            fiber   (1),    -- Optical port
            copper  (2),    -- Electrical port
            na      (3)     -- Not applicable
        }
        MAX-ACCESS read-write
        STATUS obsolete
        DESCRIPTION "Active port on combo interface."
        ::= { hpnicfifXXEntry 22 }

    hpnicfifBMbpsMulSuppressionMax OBJECT-TYPE
        SYNTAX  Integer32
        MAX-ACCESS read-only
        STATUS current
        DESCRIPTION
                "The maximum value of the multicast suppression with bandwidth-based(Mbps)
                that a port can be configured."
        ::= { hpnicfifXXEntry 23 }

    hpnicfifBMbpsMulSuppression OBJECT-TYPE
        SYNTAX  Integer32
        MAX-ACCESS read-write
        STATUS current
        DESCRIPTION
                "With bandwidth-based multicast suppression, the bandwidth is measured
                in Mbps.
                The upper limit of the multicast suppession with bandwidth-based(Mbps)
                is the value of hpnicfifBMbpsMulSuppressionMax in the entry.
                The default value of hpnicfifBMbpsMulSuppression is the value of
                hpnicfifBMbpsMulSuppressionMax."
        ::= { hpnicfifXXEntry 24 }

    hpnicfifBKbpsMulSuppressionMax OBJECT-TYPE
        SYNTAX  Integer32
        MAX-ACCESS read-only
        STATUS current
        DESCRIPTION
                "The maximum value of the multicast suppression with bandwidth-based(Kbps)
                that a port can be configured."
        ::= { hpnicfifXXEntry 25 }

    hpnicfifBKbpsMulSuppressionStep OBJECT-TYPE
        SYNTAX  Integer32
        MAX-ACCESS read-only
        STATUS current
        DESCRIPTION
                "The step of multicast suppression with bandwidth-based(Kbps)."
        ::= { hpnicfifXXEntry 26 }

    hpnicfifBKbpsMulSuppression OBJECT-TYPE
        SYNTAX  Integer32
        MAX-ACCESS read-write
        STATUS current
        DESCRIPTION
                "With bandwidth-based multicast suppression, the bandwidth
                is measured in Kbps.
                The upper limit of the multicast suppession with bandwidth-based(Kbps)
                is the value of hpnicfifBKbpsMulSuppressionMax in the entry.
                The value of hpnicfifBKbpsMulSuppression must be multiple of the
                value of hpnicfifBKbpsMulSuppressionStep.
                The default value of hpnicfifBKbpsMulSuppression is the value of
                hpnicfifBKbpsMulSuppressionMax."
        ::= { hpnicfifXXEntry 27 }

   hpnicfifUnknownPacketDropMul OBJECT-TYPE
        SYNTAX  DropDirection
        MAX-ACCESS read-write
        STATUS current
        DESCRIPTION "Control the port's unknown-multicast packets drop. When
                     inbound direction is enabled on this port, the port will
                     drop unknown-multicast packets in inbound direction. When
                     outbound direction is enabled on this port, the port will
                     drop unknown-multicast packets in outbound direction. When
                     both directions are enabled on this port, the port will
                     drop unknown-multicast packets in both inbound and outbound
                     directions."
        DEFVAL { disable }
        ::= { hpnicfifXXEntry 28 }

   hpnicfifUnknownPacketDropUni OBJECT-TYPE
        SYNTAX  DropDirection
        MAX-ACCESS read-write
        STATUS current
        DESCRIPTION "Control the port's unknown-unicast packets drop. When
                     inbound direction is enabled on this port, the port will
                     drop unknown-unicast packets in inbound direction. When
                     outbound direction is enabled on this port, the port will
                     drop unknown-unicast packets in outbound direction. When
                     both directions are enabled on this port, the port will
                     drop unknown-unicast packets in both inbound and outbound
                     directions."
        DEFVAL { disable }
        ::= { hpnicfifXXEntry 29 }

    hpnicfifBMbpsUniSuppressionMax OBJECT-TYPE
        SYNTAX  Integer32
        MAX-ACCESS read-only
        STATUS current
        DESCRIPTION "
            The maximum value of the unicast suppression with bandwidth-based
            (Mbps) that a port can be configured."
        ::= { hpnicfifXXEntry 30 }

    hpnicfifBMbpsUniSuppression OBJECT-TYPE
        SYNTAX  Integer32
        MAX-ACCESS read-write
        STATUS current
        DESCRIPTION "
            With bandwidth-based Unicast suppression, the bandwidth is measured
            in Mbps.
            The upper limit of the unicast suppession with bandwidth-based(Mbps)
            is the value of hpnicfifBMbpsUniSuppressionMax in the entry.
            The default value of hpnicfifBMbpsUniSuppression is the value of
            hpnicfifBMbpsUniSuppressionMax."
        ::= { hpnicfifXXEntry 31 }

    hpnicfifBKbpsUniSuppressionMax OBJECT-TYPE
        SYNTAX  Integer32
        MAX-ACCESS read-only
        STATUS current
        DESCRIPTION "
            The maximum value of the unicast suppression with bandwidth-based
            (Kbps) that a port can be configured."
        ::= { hpnicfifXXEntry 32 }

    hpnicfifBKbpsUniSuppressionStep OBJECT-TYPE
        SYNTAX  Integer32
        MAX-ACCESS read-only
        STATUS current
        DESCRIPTION "
            The step of unicast suppression with bandwidth-based(Kbps)."
        ::= { hpnicfifXXEntry 33 }

    hpnicfifBKbpsUniSuppression OBJECT-TYPE
        SYNTAX  Integer32
        MAX-ACCESS read-write
        STATUS current
        DESCRIPTION "
            With bandwidth-based unicast suppression, the bandwidth
            is measured in Kbps.
            The upper limit of the unicast suppession with bandwidth-based(Kbps)
            is the value of hpnicfifBKbpsUniSuppressionMax in the entry.
            The value of hpnicfifBKbpsUniSuppression must be multiple of the
            value of hpnicfifBKbpsUniSuppressionStep.
            The default value of hpnicfifBKbpsUniSuppression is the value of
            hpnicfifBKbpsUniSuppressionMax."
        ::= { hpnicfifXXEntry 34 }

    hpnicfifOutPayloadOctets OBJECT-TYPE
        SYNTAX  Counter64
        MAX-ACCESS read-only
        STATUS current
        DESCRIPTION "
            The actual output octets of the interface."
        ::= { hpnicfifXXEntry 35 }

    hpnicfifInPayloadOctets OBJECT-TYPE
        SYNTAX  Counter64
        MAX-ACCESS read-only
        STATUS current
        DESCRIPTION "
            The actual input octets of the interface."
        ::= { hpnicfifXXEntry 36 }

    hpnicfifInErrorPktsRate OBJECT-TYPE
        SYNTAX  Integer32
        MAX-ACCESS read-only
        STATUS current
        DESCRIPTION "
            The rate of inbound error packets on the interface."
        ::= { hpnicfifXXEntry 37 }

    hpnicfifInPkts OBJECT-TYPE
        SYNTAX  Counter64
        MAX-ACCESS read-only
        STATUS current
        DESCRIPTION "
            The number of packets received on the interface."
        ::= { hpnicfifXXEntry 38 }

    hpnicfifInNormalPkts OBJECT-TYPE
        SYNTAX  Counter64
        MAX-ACCESS read-only
        STATUS current
        DESCRIPTION "
            The number of normal packets received on the interface."
        ::= { hpnicfifXXEntry 39 }

    hpnicfifOutPkts OBJECT-TYPE
        SYNTAX  Counter64
        MAX-ACCESS read-only
        STATUS current
        DESCRIPTION "
            The number of packets sent on the interface."
        ::= { hpnicfifXXEntry 40 }

   hpnicfifMulSuppressionFlag OBJECT-TYPE
        SYNTAX  INTEGER
        {
            all      (1),    -- known and unknown traffic
            unknown  (2)    -- only unknown traffic
        }
        MAX-ACCESS read-write
        STATUS current
        DESCRIPTION "
            The multicast suppression flag.  If only unknown multicast
            traffic is suppressed, the value is unknown(2), and all(1) for suppression of all traffic (unknown and known)."
        ::= { hpnicfifXXEntry 41 }

    hpnicfifAggregateTable  OBJECT-TYPE
        SYNTAX SEQUENCE OF HpnicfIfAggregateEntry
        MAX-ACCESS not-accessible
        STATUS current
        DESCRIPTION "Port aggregation information table."
        ::= { hpnicfLswExtInterface  2 }


    hpnicfifAggregateEntry  OBJECT-TYPE
        SYNTAX HpnicfIfAggregateEntry
        MAX-ACCESS not-accessible
        STATUS current
        DESCRIPTION "Port aggregation information table."
        INDEX   { hpnicfifAggregatePortIndex }
        ::= { hpnicfifAggregateTable 1}

    HpnicfIfAggregateEntry  ::=
    SEQUENCE {
        hpnicfifAggregatePortIndex      InterfaceIndex,
        hpnicfifAggregatePortName       OCTET STRING,
        hpnicfifAggregatePortListPorts  PortList,
        hpnicfifAggregateModel          INTEGER,
        hpnicfifAggregateOperStatus     RowStatus
        }



    hpnicfifAggregatePortIndex  OBJECT-TYPE
        SYNTAX  InterfaceIndex
        MAX-ACCESS read-only
        STATUS current
        DESCRIPTION "Index number of the main aggregated port."
        ::= { hpnicfifAggregateEntry 1 }


    hpnicfifAggregatePortName  OBJECT-TYPE
        SYNTAX  OCTET STRING (SIZE(0..40))
        MAX-ACCESS read-write
        STATUS current
        DESCRIPTION "Aggregation group name."
        ::= { hpnicfifAggregateEntry 2 }


    hpnicfifAggregatePortListPorts OBJECT-TYPE
        SYNTAX  PortList
        MAX-ACCESS read-write
        STATUS current
        DESCRIPTION   "Portlist of a aggregating."
        ::= { hpnicfifAggregateEntry 3 }


    hpnicfifAggregateModel  OBJECT-TYPE
        SYNTAX  INTEGER
        {
        ingress     (1),
        both        (2),
        round-robin (3)
        }
        MAX-ACCESS read-write
        STATUS current
        DESCRIPTION "Load sharing mode for the port aggregation."
        ::= { hpnicfifAggregateEntry 4 }


    hpnicfifAggregateOperStatus  OBJECT-TYPE
        SYNTAX  RowStatus
        MAX-ACCESS read-create
        STATUS current
        DESCRIPTION "Current operation status of the row."
        ::= { hpnicfifAggregateEntry 5 }

-- ==================================================================
    hpnicfifHybridPortTable  OBJECT-TYPE
        SYNTAX SEQUENCE OF HpnicfifHybridPortEntry
        MAX-ACCESS not-accessible
        STATUS current
        DESCRIPTION "Hybrid-port configuration table."
        ::= { hpnicfLswExtInterface  3 }


    hpnicfifHybridPortEntry  OBJECT-TYPE
        SYNTAX HpnicfifHybridPortEntry
        MAX-ACCESS not-accessible
        STATUS current
        DESCRIPTION "Hybrid-port configuration table."
        INDEX   { hpnicfifHybridPortIndex }
        ::= { hpnicfifHybridPortTable 1}

    HpnicfifHybridPortEntry  ::=
    SEQUENCE {
        hpnicfifHybridPortIndex            INTEGER,
        hpnicfifHybridTaggedVlanListLow    OCTET STRING,
        hpnicfifHybridTaggedVlanListHigh   OCTET STRING,
        hpnicfifHybridUnTaggedVlanListLow  OCTET STRING,
        hpnicfifHybridUnTaggedVlanListHigh OCTET STRING
        }



    hpnicfifHybridPortIndex  OBJECT-TYPE
        SYNTAX  INTEGER
        MAX-ACCESS read-only
        STATUS current
        DESCRIPTION "Index number of Hybrid-port."
        ::= { hpnicfifHybridPortEntry 1 }


    hpnicfifHybridTaggedVlanListLow  OBJECT-TYPE
        SYNTAX  OCTET STRING (SIZE(0..256))
        MAX-ACCESS read-write
        STATUS current
        DESCRIPTION "Each octet within this value specifies a set of eight
                    VLANs, with the first octet specifying VLANs 1 through
                    8, the second octet specifying VLANs 9 through 16, etc.
                    Within each octet, the most significant bit represents
                    the highest numbered VLAN, and the least significant bit
                    represents the lowest numbered VLAN. Thus, each tagged VLAN
                    of the hybrid port is represented by a single bit within
                    the value of this object. If that bit has a value of '1'
                    then that VLAN is tagged in the set of VLANs; the VLAN
                    is not tagged if its bit has a value of '0'."
        ::= { hpnicfifHybridPortEntry 2 }


    hpnicfifHybridTaggedVlanListHigh OBJECT-TYPE
        SYNTAX  OCTET STRING (SIZE(0..256))
        MAX-ACCESS read-write
        STATUS current
        DESCRIPTION "Each octet within this value specifies a set of eight
                    VLANs, with the first octet specifying VLANs 2049 through
                    2056, the second octet specifying VLANs 2057 through 2064,
                    etc. Within each octet, the most significant bit represents
                    the highest numbered VLAN, and the least significant bit
                    represents the lowest numbered VLAN. Thus, each tagged VLAN
                    of the hybrid port is represented by a single bit within
                    the value of this object. If that bit has a value of '1'
                    then that VLAN is tagged in the set of VLANs; the VLAN
                    is not tagged if its bit has a value of '0'."
        ::= { hpnicfifHybridPortEntry 3 }


    hpnicfifHybridUnTaggedVlanListLow  OBJECT-TYPE
        SYNTAX  OCTET STRING (SIZE(0..256))
        MAX-ACCESS read-write
        STATUS current
        DESCRIPTION "Each octet within this value specifies a set of eight
                    VLANs, with the first octet specifying VLANs 1 through
                    8, the second octet specifying VLANs 9 through 16, etc.
                    Within each octet, the most significant bit represents
                    the highest numbered VLAN, and the least significant bit
                    represents the lowest numbered VLAN. Thus, each untagged
                    VLAN of the hybrid port is represented by a single bit
                    within the value of this object. If that bit has a value
                    of '1' then that VLAN is untagged in the set of VLANs; the
                    VLAN is not untagged if its bit has a value of '0'."
        ::= { hpnicfifHybridPortEntry 4 }


    hpnicfifHybridUnTaggedVlanListHigh OBJECT-TYPE
        SYNTAX  OCTET STRING (SIZE(0..256))
        MAX-ACCESS read-write
        STATUS current
        DESCRIPTION "Each octet within this value specifies a set of eight
                    VLANs, with the first octet specifying VLANs 2049 through
                    2056, the second octet specifying VLANs 2057 through 2064,
                    etc. Within each octet, the most significant bit represents
                    the highest numbered VLAN, and the least significant bit
                    represents the lowest numbered VLAN. Thus, each untagged
                    VLAN of the hybrid port is represented by a single bit
                    within the value of this object. If that bit has a value of
                    '1' then that VLAN is untagged in the set of VLANs; the VLAN
                    is not untagged if its bit has a value of '0'."
        ::= { hpnicfifHybridPortEntry 5 }

-- ==================== Combo port table ============================
    hpnicfifComboPortTable  OBJECT-TYPE
        SYNTAX SEQUENCE OF HpnicfifComboPortEntry
        MAX-ACCESS not-accessible
        STATUS current
        DESCRIPTION "Combo-port table."
        ::= { hpnicfLswExtInterface  4 }

    hpnicfifComboPortEntry  OBJECT-TYPE
        SYNTAX HpnicfifComboPortEntry
        MAX-ACCESS not-accessible
        STATUS current
        DESCRIPTION "The entry of hpnicfifComboPortTable."
        INDEX    { hpnicfifComboPortIndex }
        ::= { hpnicfifComboPortTable 1}

    HpnicfifComboPortEntry  ::=
    SEQUENCE {
        hpnicfifComboPortIndex       InterfaceIndex,
        hpnicfifComboPortCurActive   INTEGER
        }

    hpnicfifComboPortIndex OBJECT-TYPE
        SYNTAX  InterfaceIndex
        MAX-ACCESS read-only
        STATUS current
        DESCRIPTION
            "The combo-port interface index. Its value is the same as the value
            of ifIndex in ifTable, but only includes indexes of the combo-port
            interfaces."
        ::= { hpnicfifComboPortEntry 1 }

    hpnicfifComboPortCurActive OBJECT-TYPE
        SYNTAX  INTEGER
        {
            fiber   (1),    -- Optical port
            copper  (2),    -- Electrical port
            na      (3)     -- Not applicable
        }
        MAX-ACCESS read-write
        STATUS current
        DESCRIPTION
            "Current active interface of combo interfaces. The value 'fiber'
            means the interface with fiber connector of the pair of combo-port
            interfaces is active. The value 'copper' means the interface with
            copper connector of the pair is active. The value 'na' means not
            supported."
        ::= { hpnicfifComboPortEntry 2 }

-- ======================pkt buf table===============================
    hpnicfifPktBufTable  OBJECT-TYPE
        SYNTAX SEQUENCE OF HpnicfifPktBufEntry
        MAX-ACCESS not-accessible
        STATUS current
        DESCRIPTION "Packet buffer table."
        ::= { hpnicfLswExtInterface  5 }

    hpnicfifPktBufEntry  OBJECT-TYPE
        SYNTAX HpnicfifPktBufEntry
        MAX-ACCESS not-accessible
        STATUS current
        DESCRIPTION "The entry of hpnicfifPktBufTable."
        INDEX { ifIndex }
        ::= { hpnicfifPktBufTable 1}

    HpnicfifPktBufEntry  ::=
        SEQUENCE {
            hpnicfifPktBufFree      Integer32,
            hpnicfifPktBufInit      Integer32,
            hpnicfifPktBufMin       Integer32,
            hpnicfifPktBufMiss      Counter64,
            hpnicfifPktBufInDrop    Counter64,
            hpnicfifPktBufEgDrop    Counter64
            }

    hpnicfifPktBufFree OBJECT-TYPE
        SYNTAX  Integer32
        MAX-ACCESS read-only
        STATUS current
        DESCRIPTION
            "The number of packet buffers available for the interface."
        ::= { hpnicfifPktBufEntry 1 }

    hpnicfifPktBufInit OBJECT-TYPE
        SYNTAX  Integer32
        MAX-ACCESS read-only
        STATUS current
        DESCRIPTION
            "The number of packet buffers allocated when the interface was created."
        ::= { hpnicfifPktBufEntry 2 }

    hpnicfifPktBufMin OBJECT-TYPE
        SYNTAX  Integer32
        MAX-ACCESS read-only
        STATUS current
        DESCRIPTION
            "The smallest number of packet buffers available for the interface."
        ::= { hpnicfifPktBufEntry 3 }

    hpnicfifPktBufMiss OBJECT-TYPE
        SYNTAX  Counter64
        MAX-ACCESS read-only
        STATUS current
        DESCRIPTION
            "The number of times that the interface failed to obtain a packet
             buffer.  Failure to obtain a buffer indicates that buffers were busy."
        ::= { hpnicfifPktBufEntry 4 }

    hpnicfifPktBufInDrop OBJECT-TYPE
        SYNTAX  Counter64
        MAX-ACCESS read-only
        STATUS current
        DESCRIPTION
            "The number of ingress packets dropped by the interface
             because of insufficient data buffer."
        ::= { hpnicfifPktBufEntry 5 }

    hpnicfifPktBufEgDrop OBJECT-TYPE
        SYNTAX  Counter64
        MAX-ACCESS read-only
        STATUS current
        DESCRIPTION
            "The number of egress packets dropped by the interface
             because of insufficient data buffer."
        ::= { hpnicfifPktBufEntry 6 }

-- ======================if queue pkt buf table===============================
    hpnicfifQueuePktBufTable  OBJECT-TYPE
        SYNTAX SEQUENCE OF HpnicfifQueuePktBufEntry
        MAX-ACCESS not-accessible
        STATUS current
        DESCRIPTION "802.1p queue of the interface packet buffer table."
        ::= { hpnicfLswExtInterface  6 }

    hpnicfifQueuePktBufEntry  OBJECT-TYPE
        SYNTAX HpnicfifQueuePktBufEntry
        MAX-ACCESS not-accessible
        STATUS current
        DESCRIPTION "The entry of hpnicfifQueuePktBufTable."
        INDEX
            {
                ifIndex,
                hpnicfifQueueId
            }
        ::= { hpnicfifQueuePktBufTable 1}

    HpnicfifQueuePktBufEntry  ::=
        SEQUENCE {
            hpnicfifQueueId             Integer32,
            hpnicfifQueuePktBufTotal    Unsigned32,
            hpnicfifQueueBufUsed        Unsigned32,
            hpnicfifQueueBufThreCount   Counter32
            }

    hpnicfifQueueId OBJECT-TYPE
        SYNTAX  Integer32(1..8)
        MAX-ACCESS read-only
        STATUS current
        DESCRIPTION
            "The 802.1p queue ID of the interface. This value is
             used to specify the queue ID of the interface
             when the user wants to read one queue of the interface.
             The index number 1-8 correspond with 802.1p queue ID 0-7."
        ::= { hpnicfifQueuePktBufEntry 1 }

    hpnicfifQueuePktBufTotal OBJECT-TYPE
        SYNTAX  Unsigned32
        MAX-ACCESS read-only
        STATUS current
        DESCRIPTION
            "The number of packet buffers available for the interface,
             including fixed buffer and shared buffer."
        ::= { hpnicfifQueuePktBufEntry 2 }

    hpnicfifQueueBufUsed OBJECT-TYPE
        SYNTAX  Unsigned32
        MAX-ACCESS read-only
        STATUS current
        DESCRIPTION
            "The number of packet buffers that have been used for each
             802.1p queue of the interface."
        ::= { hpnicfifQueuePktBufEntry 3 }

    hpnicfifQueueBufThreCount OBJECT-TYPE
        SYNTAX  Counter32
        MAX-ACCESS read-only
        STATUS current
        DESCRIPTION
            "The number of times that each 802.1p queue of the interface has
             exceeded the buffer threshold. The threshold is configurated by user."
        ::= { hpnicfifQueuePktBufEntry 4 }

-- ========================l2========================================
    hpnicfLswL2InfMibObject OBJECT IDENTIFIER ::= {  hpnicfLswL2InfMib 1  }

    hpnicfSlotPortMax  OBJECT-TYPE
        SYNTAX  INTEGER
        MAX-ACCESS read-only
        STATUS current
        DESCRIPTION "Max ports of the slots."
        ::= { hpnicfLswL2InfMibObject  1 }

    hpnicfSwitchPortMax  OBJECT-TYPE
        SYNTAX  INTEGER
        MAX-ACCESS read-only
        STATUS current
        DESCRIPTION "Max ports that this switch includes."
        ::= { hpnicfLswL2InfMibObject  2 }

    hpnicfifVLANTrunkStatusTable  OBJECT-TYPE
        SYNTAX SEQUENCE OF HpnicfIfVLANTrunkStatusEntry
        MAX-ACCESS not-accessible STATUS   current
        DESCRIPTION "Gvrp attributes on the VlanTrunk port."
        ::= { hpnicfLswL2InfMibObject  3 }

    hpnicfifVLANTrunkStatusEntry  OBJECT-TYPE
        SYNTAX HpnicfIfVLANTrunkStatusEntry
        MAX-ACCESS not-accessible STATUS   current
        DESCRIPTION "Gvrp attributes on the VlanTrunk port."
        INDEX   { hpnicfifVLANTrunkIndex }
        ::= { hpnicfifVLANTrunkStatusTable 1}

    HpnicfIfVLANTrunkStatusEntry    ::=
    SEQUENCE {
        hpnicfifVLANTrunkIndex              InterfaceIndex,
        hpnicfifVLANTrunkGvrpRegistration   INTEGER,
        hpnicfifVLANTrunkPassListLow        OCTET STRING,
        hpnicfifVLANTrunkPassListHigh       OCTET STRING,
        hpnicfifVLANTrunkAllowListLow       OCTET STRING,
        hpnicfifVLANTrunkAllowListHigh      OCTET STRING
        }



    hpnicfifVLANTrunkIndex  OBJECT-TYPE
        SYNTAX  InterfaceIndex
        MAX-ACCESS read-only
        STATUS current
        DESCRIPTION "Index number of the VLANTrunk interface."
        ::= { hpnicfifVLANTrunkStatusEntry 1 }


    hpnicfifVLANTrunkGvrpRegistration OBJECT-TYPE
        SYNTAX  INTEGER
        {
        normal  (1),
        fixed   (2),
        forbidden   (3)
        }
        MAX-ACCESS read-write
        STATUS current
        DESCRIPTION
            "GVRP registration information
            normal:     This is the default configuration. Allow create, register
                        and unregister vlans dynamiclly at this port.
            fixed:      Aallow create and register vlan manually at this port.
                        Prevent from unregistering vlans or registering known
                        vlans of this port at another trunk port.
            forbidden:  Unregister all vlans but vlan 1, forbid to create or
                        register any other vlans at this port."
        ::= { hpnicfifVLANTrunkStatusEntry 2 }


    hpnicfifVLANTrunkPassListLow OBJECT-TYPE
        SYNTAX  OCTET STRING
        MAX-ACCESS read-only
        STATUS current
        DESCRIPTION "Each octet within this value specifies a set of eight
                    VLANs, with the first octet specifying VLANs 1 through
                    8, the second octet specifying VLANs 9 through 16, etc.
                    Within each octet, the most significant bit represents
                    the highest numbered VLAN, and the least significant bit
                    represents the lowest numbered VLAN. Thus, each actually
                    passed VLAN of the trunk port is represented by a single
                    bit within the value of this object. If that bit has a
                    value of '1' then that VLAN is actually passed in the set
                    of VLANs; the VLAN is not actually passed if its bit has
                    a value of '0'."
        ::= { hpnicfifVLANTrunkStatusEntry 4 }

    hpnicfifVLANTrunkPassListHigh OBJECT-TYPE
        SYNTAX  OCTET STRING
        MAX-ACCESS read-only
        STATUS current
        DESCRIPTION "Each octet within this value specifies a set of eight
                    VLANs, with the first octet specifying VLANs 2049 through
                    2056, the second octet specifying VLANs 2057 through 2064,
                    etc. Within each octet, the most significant bit represents
                    the highest numbered VLAN, and the least significant bit
                    represents the lowest numbered VLAN. Thus, each actually
                    passed VLAN of the trunk port is represented by a single
                    bit within the value of this object. If that bit has a
                    value of '1' then that VLAN is actually passed in the set
                    of VLANs; the VLAN is not actually passed if its bit has
                    a value of '0'."
        ::= { hpnicfifVLANTrunkStatusEntry 5 }

    hpnicfifVLANTrunkAllowListLow OBJECT-TYPE
        SYNTAX  OCTET STRING
        MAX-ACCESS read-write
        STATUS current
        DESCRIPTION "Each octet within this value specifies a set of eight
                    VLANs, with the first octet specifying VLANs 1 through
                    8, the second octet specifying VLANs 9 through 16, etc.
                    Within each octet, the most significant bit represents
                    the highest numbered VLAN, and the least significant bit
                    represents the lowest numbered VLAN. Thus, each allowed
                    VLAN of the trunk port is represented by a single bit
                    within the value of this object. If that bit has a value
                    of '1' then that VLAN is allowed in the set of VLANs;
                    the VLAN is not allowed if its bit has a value of '0'."
        ::= { hpnicfifVLANTrunkStatusEntry 6 }

    hpnicfifVLANTrunkAllowListHigh OBJECT-TYPE
        SYNTAX  OCTET STRING
        MAX-ACCESS read-write
        STATUS current
        DESCRIPTION "Each octet within this value specifies a set of eight
                    VLANs, with the first octet specifying VLANs 2049 through
                    2056, the second octet specifying VLANs 2057 through 2064,
                    etc. Within each octet, the most significant bit represents
                    the highest numbered VLAN, and the least significant bit
                    represents the lowest numbered VLAN. Thus, each allowed
                    VLAN of the trunk port is represented by a single bit within
                    the value of this object. If that bit has a value of '1'
                    then that VLAN is allowed in the set of VLANs; the VLAN is
                    not allowed if its bit has a value of '0'."
        ::= { hpnicfifVLANTrunkStatusEntry 7 }




    hpnicfethernetTable  OBJECT-TYPE
        SYNTAX SEQUENCE OF HpnicfEthernetEntry
        MAX-ACCESS not-accessible
        STATUS current
        DESCRIPTION "Ethernet port attribute table."
        ::= { hpnicfLswL2InfMibObject  4 }


    hpnicfethernetEntry  OBJECT-TYPE
        SYNTAX HpnicfEthernetEntry
        MAX-ACCESS not-accessible
        STATUS current
        DESCRIPTION "Entries of Ethernet port attribute table"
        INDEX { ifIndex }
        ::= { hpnicfethernetTable 1}

    HpnicfEthernetEntry ::=
    SEQUENCE {
        hpnicfifEthernetDuplex          INTEGER,
        hpnicfifEthernetMTU             INTEGER,
        hpnicfifEthernetSpeed           INTEGER,
        hpnicfifEthernetMdi             INTEGER,
        hpnicfMaxMacLearn               INTEGER,
        hpnicfifMacAddressLearn         INTEGER,
        hpnicfifEthernetTest            INTEGER,
        hpnicfifMacAddrLearnMode        INTEGER,
        hpnicfifEthernetFlowInterval    INTEGER,
        hpnicfifEthernetIsolate         OCTET STRING,
        hpnicfifVlanVPNStatus           INTEGER,
        hpnicfifVlanVPNUplinkStatus     INTEGER,
        hpnicfifVlanVPNTPID             Integer32,
        hpnicfifIsolateGroupID          Integer32,
        hpnicfifisUplinkPort            INTEGER,
        hpnicfifEthernetAutoSpeedMask   SpeedModeFlag,
        hpnicfifEthernetAutoSpeed       SpeedModeFlag
        }

    hpnicfifEthernetDuplex OBJECT-TYPE
        SYNTAX  INTEGER
        {
        full    (1),
        half    (2),
        auto    (3)
        }
        MAX-ACCESS read-write
        STATUS current
        DESCRIPTION "Ethernet interface mode."
        ::= { hpnicfethernetEntry 3 }


    hpnicfifEthernetMTU  OBJECT-TYPE
        SYNTAX  INTEGER
        MAX-ACCESS read-write
        STATUS current
        DESCRIPTION "MTU on the Ethernet interface."
        ::= { hpnicfethernetEntry 4 }


    hpnicfifEthernetSpeed OBJECT-TYPE
        SYNTAX  INTEGER
        {
        auto    (0),
        s10M    (10),
        s100M   (100),
        s1000M  (1000),
        s10000M (10000),
        s24000M (24000),
        s40000M (40000),
        s100000M (100000)
        }
        MAX-ACCESS read-write
        STATUS current
        DESCRIPTION "Ethernet interface speed."
        ::= { hpnicfethernetEntry 5 }

    hpnicfifEthernetMdi OBJECT-TYPE
        SYNTAX  INTEGER
        {
        mdi-ii   (1),
        mdi-x   (2),
        mdi-auto   (3)
        }
        MAX-ACCESS read-write
        STATUS current
        DESCRIPTION
            "Type of the line connected to the port.
            MDI-II (straight-through cable): 1
            MDI-X (crossover cable): 2
            MDI-AUTO (auto-sensing): 3"
        ::= { hpnicfethernetEntry 7 }

    hpnicfMaxMacLearn OBJECT-TYPE
        SYNTAX  INTEGER(-1..2147483647)
        MAX-ACCESS read-write
        STATUS current
        DESCRIPTION
            "The maximum number of MAC addresses that the port can learn.
            The value -1 means that the number of Mac addresses that the port
            can learn is unlimited."
        ::= { hpnicfethernetEntry 8 }

    hpnicfifMacAddressLearn OBJECT-TYPE
        SYNTAX  INTEGER
        {
            enabled(1),
            disabled(2)
        }
        MAX-ACCESS read-only
        STATUS current
        DESCRIPTION
            "This object indicates if the interface is allowed to learn mac address.
            eanbled(1) means the interface can learn mac address, otherwise disabled(2)
            can be set."
        ::= { hpnicfethernetEntry 9 }

    hpnicfifEthernetTest OBJECT-TYPE
        SYNTAX  INTEGER
        {
            test(1)
        }
        MAX-ACCESS read-write
        STATUS current
        DESCRIPTION
            "Test this interface.
            The actual testing will be different according to products.
            Read operation not supported."
        ::= { hpnicfethernetEntry 10 }

    hpnicfifMacAddrLearnMode OBJECT-TYPE
        SYNTAX  INTEGER
        {
            iVL(1),
            sVL(2)
        }
        MAX-ACCESS read-only
        STATUS current
        DESCRIPTION
            "Status indicates mac address learn mode of the interface.
            IVL(1) means independent VLAN learning.
            SVL means shared VLAN learning."
        ::= { hpnicfethernetEntry 11 }

    hpnicfifEthernetFlowInterval OBJECT-TYPE
        SYNTAX  INTEGER (5..300)
        MAX-ACCESS read-write
        STATUS current
        DESCRIPTION
            "Set flow interval of the ethernet.
            The NMS should set value to integer which is a multiple of 5."
        ::= { hpnicfethernetEntry 12 }

    hpnicfifEthernetIsolate  OBJECT-TYPE
        SYNTAX  OCTET STRING
        MAX-ACCESS read-write
        STATUS current
        DESCRIPTION
            "Isolate group means that all ports in the same isolate group can not
            send and receive packets each other.
            Each octet within this value specifies a set of eight isolate groups,
            with the first octet specifying isolate groups 1 through 8,  the second
            octet specifying isolate groups 9 through 16, etc. Within each octet,
            the leftmost bit is the first bit.
            the first bit represents the lowest numbered isolate group, and the
            last bit represents the highest numbered isolate group. one port can
            belong to more than one isolate group.
            Thus, each isolate group is represented by a single bit within the
            value of this object.
            If that bit has a value of '1', then that isolate group includes this port;
            the port is not included if its bit has a value of '0'.
            for example, the first octet is '10000100' means that the port is
            included in the isolate group 1 and isolate group 6."
        ::= { hpnicfethernetEntry 13 }

    hpnicfifVlanVPNStatus OBJECT-TYPE
        SYNTAX  INTEGER
        {
             enabled(1),
             disabled(2)
        }
        MAX-ACCESS read-write
        STATUS current
        DESCRIPTION "Vlan VPN enable status."
        ::= { hpnicfethernetEntry 14 }

    hpnicfifVlanVPNUplinkStatus OBJECT-TYPE
        SYNTAX  INTEGER
        {
             enabled(1),
             disabled(2)
        }
        MAX-ACCESS read-write
        STATUS current
        DESCRIPTION "Vlan VPN uplink status."
        ::= { hpnicfethernetEntry 15 }

    hpnicfifVlanVPNTPID OBJECT-TYPE
        SYNTAX  Integer32 (1..65535)
        MAX-ACCESS read-write
        STATUS current
        DESCRIPTION
            "Port based Vlan VPN TPID(Tag Protocol Indentifier), default value
            is 0x8100.
            Please refer to hpnicfVlanVPNTPIDMode to get more information."
        ::= { hpnicfethernetEntry 16 }

    hpnicfifIsolateGroupID OBJECT-TYPE
        SYNTAX  Integer32
        MAX-ACCESS read-write
        STATUS current
        DESCRIPTION
            "Isolate group identifier. Value zero means this interface does not
            belong to any isolate group."
        ::= { hpnicfethernetEntry 17 }

    hpnicfifisUplinkPort OBJECT-TYPE
        SYNTAX  INTEGER
        {
             yes(1),
             no(2)
        }
        MAX-ACCESS read-only
        STATUS current
        DESCRIPTION
            "Ethernet uplink status, default value is 2."
        ::= { hpnicfethernetEntry 18 }

    hpnicfifEthernetAutoSpeedMask OBJECT-TYPE
        SYNTAX  SpeedModeFlag
        MAX-ACCESS read-only
        STATUS current
        DESCRIPTION
            "This object specifies which kinds of speed mode can be negotiated.
            Each bit corresponds to a kind of speed mode.

            If the value of a bit is '1', it means the corresponding speed mode
            is negotiable on the port. Otherwise the negotiation for that
            kind of speed mode is not supported on this port. If there are
            several negotiable speed modes, all bits for them  are '1'.
            For example, if the speed mode 's10M' and 's1000M' can be negotiable,
            the value of this object is 0xA0."
        ::= { hpnicfethernetEntry 19 }

    hpnicfifEthernetAutoSpeed OBJECT-TYPE
        SYNTAX  SpeedModeFlag
        MAX-ACCESS read-write
        STATUS  current
        DESCRIPTION
            "This object indicates which kinds of speed mode are negotiable
            on this port.

            Only when a bit of hpnicfifEthernetAutoSpeedMask is '1', the corresponding
            bit of this object can be set to '1', indicating the corresponding
            speed mode is negotiable.

            For example, if the value of hpnicfifEthernetAutoSpeedMask is 0xA0,
            which indicates speed mode 's10M' and 's1000M' are negotiable,
            the possible value of this object should be one of the four values
            (0x00, 0x20, 0x80 and 0xA0).

            If the value of hpnicfifEthernetSpeed is not 'auto', the value of this
            object is insignificant and should be ignored. The value length of
            this object should be as long as that of hpnicfifEthernetAutoSpeedMask."
        ::= { hpnicfethernetEntry 20 }

    hpnicfIsolateGroupMax  OBJECT-TYPE
        SYNTAX  Integer32
        MAX-ACCESS read-only
        STATUS current
        DESCRIPTION
            "Max isolate group that this device support, the value is zero
            means that the device does not support isolate group."
        ::= { hpnicfLswL2InfMibObject  5 }

   hpnicfGlobalBroadcastMaxPps   OBJECT-TYPE
        SYNTAX INTEGER   (0..14881000)
        MAX-ACCESS read-write
        STATUS  current
        DESCRIPTION
            "The global max packets per second. When it is set, the value of
            BroadcastMaxPps in all ports will be changed to that setting."
        ::= { hpnicfLswL2InfMibObject 6 }

  hpnicfGlobalBroadcastMaxRatio OBJECT-TYPE
        SYNTAX INTEGER (0..100)
        MAX-ACCESS read-write
        STATUS  current
        DESCRIPTION
            "The global max-ratio of broadcast from 0 to 100 percent.
            When it is set, the value of BroadcastMaxRatio in all ports
            will be changed to that setting."
        ::= { hpnicfLswL2InfMibObject 7  }

    hpnicfBpduTunnelStatus  OBJECT-TYPE
        SYNTAX  INTEGER
        {
             enabled(1),
             disabled(2)
        }
        MAX-ACCESS read-write
        STATUS current
        DESCRIPTION "Bpdu tunnel enable status."
        ::= { hpnicfLswL2InfMibObject  8 }

   hpnicfVlanVPNTPIDMode OBJECT-TYPE
        SYNTAX  INTEGER
        {
             port-based(1),
             global(2)
        }
        MAX-ACCESS read-only
        STATUS current
        DESCRIPTION
            "Vlan VPN TPID mode.

            The value 'port-based' means VLAN VPN TPID value would be set based
            on port via hpnicfifVlanVPNTPID. In this situation, hpnicfVlanVPNTPID is
            meaningless and always return 0x8100.

            The value 'global' means VLAN VPN TPID value should be set globally
            via hpnicfVlanVPNTPID. In this situation, hpnicfifVlanVPNTPID in hpnicfethernetTable
            has the same value with hpnicfVlanVPNTPID."
      ::= { hpnicfLswL2InfMibObject  9 }

   hpnicfVlanVPNTPID OBJECT-TYPE
        SYNTAX  Integer32 (1..65535)
        MAX-ACCESS read-write
        STATUS current
        DESCRIPTION
            "Global Vlan VPN TPID(Tag Protocol Indentifier), default value
            is 0x8100."
        ::= { hpnicfLswL2InfMibObject  10 }

   hpnicfPortIsolateGroupTable  OBJECT-TYPE
        SYNTAX SEQUENCE OF HpnicfPortIsolateGroupEntry
        MAX-ACCESS not-accessible
        STATUS current
        DESCRIPTION "Isolate Group attribute table."
        ::= { hpnicfLswL2InfMibObject  11 }


   hpnicfPortIsolateGroupEntry  OBJECT-TYPE
        SYNTAX HpnicfPortIsolateGroupEntry
        MAX-ACCESS not-accessible
        STATUS current
        DESCRIPTION "The entry of hpnicfPortIsolateGroupTable."
        INDEX    { hpnicfPortIsolateGroupIndex }
        ::= { hpnicfPortIsolateGroupTable 1 }

    HpnicfPortIsolateGroupEntry ::=
    SEQUENCE {
        hpnicfPortIsolateGroupIndex              Integer32,
        hpnicfPortIsolateUplinkIfIndex           InterfaceIndex,
        hpnicfPortIsolateGroupRowStatus          RowStatus,
        hpnicfPortIsolateGroupDescription        DisplayString
        }

   hpnicfPortIsolateGroupIndex OBJECT-TYPE
        SYNTAX  Integer32
        MAX-ACCESS not-accessible
        STATUS current
        DESCRIPTION
            "Port isolate group identifier.
            The index of the hpnicfPortIsolateGroupTable.
            The value ranges from 1 to the limit of isolate group quantity."
        ::= { hpnicfPortIsolateGroupEntry 1 }

   hpnicfPortIsolateUplinkIfIndex  OBJECT-TYPE
        SYNTAX  InterfaceIndex
        MAX-ACCESS read-create
        STATUS current
        DESCRIPTION "Index number of the uplink interface."
        ::= { hpnicfPortIsolateGroupEntry 2 }

    hpnicfPortIsolateGroupRowStatus OBJECT-TYPE
        SYNTAX  RowStatus
        MAX-ACCESS read-create
        STATUS current
        DESCRIPTION
            "Current operation status of the row."
        ::= { hpnicfPortIsolateGroupEntry  3 }

    hpnicfPortIsolateGroupDescription OBJECT-TYPE
        SYNTAX  DisplayString (SIZE(0..80))
        MAX-ACCESS read-create
        STATUS current
        DESCRIPTION
            "Port isolate group description, default value is zero-length string."
        ::= { hpnicfPortIsolateGroupEntry 4 }

    hpnicfMaxMacLearnRange OBJECT-TYPE
        SYNTAX  Integer32
        MAX-ACCESS read-only
        STATUS current
        DESCRIPTION "The maximum number of MAC address that the port supports."
        ::= { hpnicfLswL2InfMibObject  12 }


    hpnicfifPortProtocolStatTable  OBJECT-TYPE
        SYNTAX SEQUENCE OF HpnicfifPortProtocolStatEntry
        MAX-ACCESS not-accessible
        STATUS current
        DESCRIPTION
            "This table contains objects of port statistics information based on
            IPv4 and IPv6 protocols."
        ::= { hpnicfLswL2InfMibObject  13 }

    hpnicfifPortProtocolStatEntry  OBJECT-TYPE
        SYNTAX HpnicfifPortProtocolStatEntry
        MAX-ACCESS not-accessible
        STATUS current
        DESCRIPTION "The entry of hpnicfifPortProtocolStatTable."
        INDEX    { ifIndex }
        ::= { hpnicfifPortProtocolStatTable 1 }

    HpnicfifPortProtocolStatEntry ::=
        SEQUENCE {
            hpnicfifIPv4InOctets                        Counter64,
            hpnicfifIPv4InUcastPkts                     Counter64,
            hpnicfifIPv4InMultiPkts                     Counter64,
            hpnicfifIPv4InBroadcastPkts                 Counter64,
            hpnicfifIPv4InDiscards                      Counter64,
            hpnicfifIPv4InErrors                        Counter64,
            hpnicfifIPv4OutOctets                       Counter64,
            hpnicfifIPv4OutUcastPkts                    Counter64,
            hpnicfifIPv4OutMultiPkts                    Counter64,
            hpnicfifIPv4OutBroadcastPkts                Counter64,
            hpnicfifIPv4OutDiscards                     Counter64,
            hpnicfifIPv4OutErrors                       Counter64,
            hpnicfifIPv6InOctets                        Counter64,
            hpnicfifIPv6InUcastPkts                     Counter64,
            hpnicfifIPv6InMultiPkts                     Counter64,
            hpnicfifIPv6InAnycastPkts                   Counter64,
            hpnicfifIPv6InDiscards                      Counter64,
            hpnicfifIPv6InErrors                        Counter64,
            hpnicfifIPv6OutOctets                       Counter64,
            hpnicfifIPv6OutUcastPkts                    Counter64,
            hpnicfifIPv6OutMultiPkts                    Counter64,
            hpnicfifIPv6OutAnycastPkts                  Counter64,
            hpnicfifIPv6OutDiscards                     Counter64,
            hpnicfifIPv6OutErrors                       Counter64
        }
    hpnicfifIPv4InOctets OBJECT-TYPE
        SYNTAX  Counter64
        MAX-ACCESS read-only
        STATUS current
        DESCRIPTION
            "Number of octets based on IPv4 received on the interface."
        ::= { hpnicfifPortProtocolStatEntry 1 }

    hpnicfifIPv4InUcastPkts OBJECT-TYPE
        SYNTAX  Counter64
        MAX-ACCESS read-only
        STATUS current
        DESCRIPTION
            "Number of unicast packets based on IPv4 received on the interface."
        ::= { hpnicfifPortProtocolStatEntry 2 }

    hpnicfifIPv4InMultiPkts OBJECT-TYPE
        SYNTAX  Counter64
        MAX-ACCESS read-only
        STATUS current
        DESCRIPTION
            "Number of multicast packets based on IPv4 received on the interface."
        ::= { hpnicfifPortProtocolStatEntry 3 }

    hpnicfifIPv4InBroadcastPkts OBJECT-TYPE
        SYNTAX  Counter64
        MAX-ACCESS read-only
        STATUS current
        DESCRIPTION
            "Number of broadcast packets based on IPv4 received on the interface."
        ::= { hpnicfifPortProtocolStatEntry 4 }

    hpnicfifIPv4InDiscards OBJECT-TYPE
        SYNTAX  Counter64
        MAX-ACCESS read-only
        STATUS current
        DESCRIPTION
            "Number of discard packets based on IPv4 received on the interface."
        ::= { hpnicfifPortProtocolStatEntry 5 }

    hpnicfifIPv4InErrors OBJECT-TYPE
        SYNTAX  Counter64
        MAX-ACCESS read-only
        STATUS current
        DESCRIPTION
            "Number of error packets based on IPv4 received on the interface."
        ::= { hpnicfifPortProtocolStatEntry 6 }

    hpnicfifIPv4OutOctets OBJECT-TYPE
        SYNTAX  Counter64
        MAX-ACCESS read-only
        STATUS current
        DESCRIPTION
            "Number of octets based on IPv4 transmitted out of the interface."
        ::= { hpnicfifPortProtocolStatEntry  7 }

    hpnicfifIPv4OutUcastPkts OBJECT-TYPE
        SYNTAX  Counter64
        MAX-ACCESS read-only
        STATUS current
        DESCRIPTION
            "Number of unicast packets based on IPv4 transmitted out of the
            interface."
        ::= { hpnicfifPortProtocolStatEntry  8 }

    hpnicfifIPv4OutMultiPkts OBJECT-TYPE
        SYNTAX  Counter64
        MAX-ACCESS read-only
        STATUS current
        DESCRIPTION
            "Number of multicast packets based on IPv4 transmitted out of the
            interface."
        ::= { hpnicfifPortProtocolStatEntry 9 }

    hpnicfifIPv4OutBroadcastPkts OBJECT-TYPE
        SYNTAX  Counter64
        MAX-ACCESS read-only
        STATUS current
        DESCRIPTION
            "Number of broadcast packets based on IPv4 transmitted out of the
            interface."
        ::= { hpnicfifPortProtocolStatEntry 10 }

    hpnicfifIPv4OutDiscards OBJECT-TYPE
        SYNTAX  Counter64
        MAX-ACCESS read-only
        STATUS current
        DESCRIPTION
            "Number of discard packets based on IPv4 transmitted out of the
            interface."
        ::= { hpnicfifPortProtocolStatEntry 11 }

    hpnicfifIPv4OutErrors OBJECT-TYPE
        SYNTAX  Counter64
        MAX-ACCESS read-only
        STATUS current
        DESCRIPTION
            "Number of error packets based on IPv4 transmitted out of the
            interface."
        ::= { hpnicfifPortProtocolStatEntry 12 }

    hpnicfifIPv6InOctets OBJECT-TYPE
        SYNTAX  Counter64
        MAX-ACCESS read-only
        STATUS current
        DESCRIPTION
            "Number of octets based on IPv6 received on the interface."
        ::= { hpnicfifPortProtocolStatEntry 13 }

    hpnicfifIPv6InUcastPkts OBJECT-TYPE
        SYNTAX  Counter64
        MAX-ACCESS read-only
        STATUS current
        DESCRIPTION
            "Number of unicast packets based on IPv6 received on the interface."
        ::= { hpnicfifPortProtocolStatEntry 14 }

    hpnicfifIPv6InMultiPkts OBJECT-TYPE
        SYNTAX  Counter64
        MAX-ACCESS read-only
        STATUS current
        DESCRIPTION
            "Number of multicast packets based on IPv6 received on the interface."
        ::= { hpnicfifPortProtocolStatEntry 15 }

    hpnicfifIPv6InAnycastPkts OBJECT-TYPE
        SYNTAX  Counter64
        MAX-ACCESS read-only
        STATUS current
        DESCRIPTION
            "Number of anycast packets based on IPv6 received on the interface."
        ::= { hpnicfifPortProtocolStatEntry 16 }

    hpnicfifIPv6InDiscards OBJECT-TYPE
        SYNTAX  Counter64
        MAX-ACCESS read-only
        STATUS current
        DESCRIPTION
            "Number of discard packets based on IPv6 received on the interface."
        ::= { hpnicfifPortProtocolStatEntry 17 }

    hpnicfifIPv6InErrors OBJECT-TYPE
        SYNTAX  Counter64
        MAX-ACCESS read-only
        STATUS current
        DESCRIPTION
            "Number of error packets based on IPv6 received on the interface."
        ::= { hpnicfifPortProtocolStatEntry 18 }

    hpnicfifIPv6OutOctets OBJECT-TYPE
        SYNTAX  Counter64
        MAX-ACCESS read-only
        STATUS current
        DESCRIPTION
            "Number of octets based on IPv6 transmitted of the interface."
        ::= { hpnicfifPortProtocolStatEntry  19 }

    hpnicfifIPv6OutUcastPkts OBJECT-TYPE
        SYNTAX  Counter64
        MAX-ACCESS read-only
        STATUS current
        DESCRIPTION
            "Number of unicast packets based on IPv6 transmitted out of the
            interface."
        ::= { hpnicfifPortProtocolStatEntry  20 }

    hpnicfifIPv6OutMultiPkts OBJECT-TYPE
        SYNTAX  Counter64
        MAX-ACCESS read-only
        STATUS current
        DESCRIPTION
            "Number of multicast packets based on IPv6 transmitted out of the
            interface."
        ::= { hpnicfifPortProtocolStatEntry 21 }

    hpnicfifIPv6OutAnycastPkts OBJECT-TYPE
        SYNTAX  Counter64
        MAX-ACCESS read-only
        STATUS current
        DESCRIPTION
            "Number of anycast packets based on IPv6 transmitted out of the
            interface."
        ::= { hpnicfifPortProtocolStatEntry 22 }

    hpnicfifIPv6OutDiscards OBJECT-TYPE
        SYNTAX  Counter64
        MAX-ACCESS read-only
        STATUS current
        DESCRIPTION
            "Number of discard packets based on IPv6 transmitted out of the
            interface."
        ::= { hpnicfifPortProtocolStatEntry 23 }

    hpnicfifIPv6OutErrors OBJECT-TYPE
        SYNTAX  Counter64
        MAX-ACCESS read-only
        STATUS current
        DESCRIPTION
            "Number of error packets based on IPv6 transmitted out of the
            interface."
        ::= { hpnicfifPortProtocolStatEntry 24 }
END
