-- ============================================================================
-- Copyright (c) 2010-2015 Hewlett-Packard Development Company, L.P.
--
-- Description: Interface QoS Management Information Base.
-- Reference: RFC 3291
-- Version: 1.9
-- History:
-- V1.0 created by tangshun.
-- V1.1 2006/02/24 modified by changhuifeng
--  Add  object hpnicfIfQoSWFQType in hpnicfIfQoSWFQTable.
--  Add hpnicfIfQoSL3PlusObjects and hpnicfIfQoSPortBindingTable.
--  Modify property of hpnicfIfQoSPortWredPreID to "not-accessible".
--  Add the  enumeration ipall to hpnicfIfQoSPQClassRuleType in hpnicfIfQoSPQClassRuleTable.
--  Modify some text errors in this file.
-- V1.2 2006/03/29 modified by xialei
--  Modify the ipv4acl value in description of hpnicfIfQoSPQClassRuleValue and hpnicfIfQoSCQClassRuleValue
--  Add the enumeration mpls to hpnicfIfQoSPQClassRuleType in hpnicfIfQoSPQClassRuleTable.
--  Add the enumeration ipall, mpls to hpnicfIfQoSCQClassRuleType in hpnicfIfQoSCQClassRuleTable.
-- V1.3 2006/05/24 add by cuichuanjin
--  Add hpnicfIfQoSCarlTable
-- V1.4 2007/11/12 modified by mouxuanli
--  Modify the description of the object hpnicfIfQoSPassPackets.
--  Add 18 objects in hpnicfIfQoSHardwareQueueRunInfoTable.
--  Add hpnicfIfQoSHQueueTcpRunInfoTable.
-- V1.5 2008/9/25 modified by yueting
--  Add hpnicfQoSIfTraStaConfigInfoTable.
--  Add hpnicfQoSIfTraStaRunInfoTable.
-- V1.6 2011/12/14 modified by mouxuanli
--  Add the enumeration byteCountWrr, byteCountWfq to hpnicfIfQoSQSMode in hpnicfIfQoSQSModeTable.
--  Add hpnicfIfQoSQSMinBandwidth in hpnicfIfQoSQSWeightTable.
--  Add hpnicfIfQoSLRPir in hpnicfIfQoSLRConfigTable.
-- V1.7 2012/04/28 modified by mouxuanli
--  Add the enumeration ipPrecedence, dot11e, auto to hpnicfIfQoSPortPriorityTrustTrustType.
--  Add the enumeration overcast to hpnicfIfQoSPortPriorityTrustOvercastType.
--  Add hpnicfIfQoSPrePriMapTable.
-- V1.8 2013/10/25 modified by mouxuanli
--  Add the enumeration gmb to hpnicfIfQoSQSMode.
--  Add hpnicfIfQoSQSMinBandwidthPercent in hpnicfIfQoSQSWeightTable.
--  Add hpnicfIfQoSLRUnit in hpnicfIfQoSLRConfigTable.
--  Add hpnicfQoSGlobalPriorityObject.
-- V1.9 2014/11/25 modified by zhaixiaoxiang & xunzhi
--  Modify the name of CarAction to HpnicfIfCarAction.
--  Add the enumeration remarkLocalPreContinue, remarkLocalPrePass, remarkDropPreContinue
--  and remarkDropPrePass to HpnicfIfCarAction and modify the related descriptions.
--  Add the enumeration hierarchy to hpnicfIfQoSAggregativeCarType.
--  Add hpnicfIfQoSTricolorCarUnitType in hpnicfIfQoSTricolorCarConfigTable.
--  Add hpnicfIfQoSGTSPir and hpnicfIfQoSGTSUnitType in hpnicfIfQoSGTSConfigTable.
--  Add hpnicfIfQoSProcessingStatus node.
-- ============================================================================
HPN-ICF-IFQOS2-MIB DEFINITIONS ::= BEGIN

        IMPORTS
            hpnicfCommon
                FROM HPN-ICF-OID-MIB
            OBJECT-TYPE, MODULE-IDENTITY, Integer32, Counter64, Unsigned32, IpAddress
                FROM SNMPv2-SMI
            ifIndex
                FROM IF-MIB
            InetAddressIPv6, InetAddressPrefixLength
                FROM INET-ADDRESS-MIB
            RowStatus, TruthValue, TEXTUAL-CONVENTION
                FROM SNMPv2-TC;
--
-- Nodes definitions
--

        hpnicfIfQos2 MODULE-IDENTITY
            LAST-UPDATED "201411250000Z"
            ORGANIZATION
                ""
            CONTACT-INFO
                ""
            DESCRIPTION
                "Interface QoS management information base."
            REVISION "201411250000Z"        --November 25, 2014 at 00:00 GMT
            DESCRIPTION
                "Add the unit type node in hpnicfIfQoSTricolorCarConfigTable and
                hpnicfIfQoSGTSConfigTable, and add object hpnicfIfQoSProcessingStatus."
            REVISION "201311280000Z"        --November 28, 2013 at 00:00 GMT
            DESCRIPTION
                "Interface QoS management information base."
            ::= { hpnicfQos2 1 }

        hpnicfQos2     OBJECT IDENTIFIER ::= { hpnicfCommon 65 }

-- IfCar Action
        HpnicfIfCarAction ::= TEXTUAL-CONVENTION
            STATUS current
            DESCRIPTION
                "The actions taken when packets conforming or exceeding the configured CIR."
            SYNTAX  INTEGER
            {
                invalid(0),
                pass(1),
                continue(2),
                discard(3),
                remark(4),
                remark-ip-continue(5),
                remark-ip-pass(6),
                remark-mplsexp-continue(7),
                remark-mplsexp-pass(8),
                remark-dscp-continue(9),
                remark-dscp-pass(10),
                remark-dot1p-continue(11),
                remark-dot1p-pass(12),
                remark-atm-clp-continue(13),
                remark-atm-clp-pass(14),
                remark-fr-de-continue(15),
                remark-fr-de-pass(16),
                remarkLocalPreContinue(17),
                remarkLocalPrePass(18),
                remarkDropPreContinue(19),
                remarkDropPrePass(20)
            }

--
-- priority queue
--
        PriorityQueue ::= TEXTUAL-CONVENTION
            STATUS current
            DESCRIPTION
                "The type of priority queue."
            SYNTAX INTEGER
            {
                top(1),
                middle(2),
                normal(3),
                bottom(4)
            }
--
-- direction
--
        Direction ::= TEXTUAL-CONVENTION
            STATUS current
            DESCRIPTION
                "Inbound or outbound."
            SYNTAX INTEGER
            {
                inbound(1),
                outbound(2)
            }
--
-- node of hpnicfIfQoSHardwareQueueObjects
--
        hpnicfIfQoSHardwareQueueObjects OBJECT IDENTIFIER ::= { hpnicfIfQos2 1 }
--
-- nodes of hpnicfIfQoSHardwareQueueConfigGroup
--
        hpnicfIfQoSHardwareQueueConfigGroup OBJECT IDENTIFIER ::= { hpnicfIfQoSHardwareQueueObjects 1 }

        hpnicfIfQoSQSModeTable OBJECT-TYPE
            SYNTAX SEQUENCE OF HpnicfIfQoSQSModeEntry
            MAX-ACCESS not-accessible
            STATUS current
            DESCRIPTION
                "A table of queue schedule mode information."
            ::= { hpnicfIfQoSHardwareQueueConfigGroup 1 }

        hpnicfIfQoSQSModeEntry OBJECT-TYPE
            SYNTAX HpnicfIfQoSQSModeEntry
            MAX-ACCESS not-accessible
            STATUS current
            DESCRIPTION
                "Queue schedule mode information entry."
            INDEX { ifIndex }
            ::= { hpnicfIfQoSQSModeTable 1 }

        HpnicfIfQoSQSModeEntry ::=
            SEQUENCE
            {
                hpnicfIfQoSQSMode
                    INTEGER
            }

        hpnicfIfQoSQSMode OBJECT-TYPE
            SYNTAX INTEGER
            {
                sp(1),
                sp0(2),
                sp1(3),
                sp2(4),
                wrr(5),
                hpnicffq(6),
                wrr-sp(7),
                byteCountWrr(8),
                byteCountWfq(9),
                gmb(10)
            }
            MAX-ACCESS read-write
            STATUS current
            DESCRIPTION
                "The mode of schedule."
            ::= { hpnicfIfQoSQSModeEntry 1 }

--
-- notes of hpnicfIfQoSQSWeightTable
--
        hpnicfIfQoSQSWeightTable OBJECT-TYPE
            SYNTAX SEQUENCE OF HpnicfIfQoSQSWeightEntry
            MAX-ACCESS not-accessible
            STATUS current
            DESCRIPTION
                "A table of queue schedule weight configuration information."
            ::= { hpnicfIfQoSHardwareQueueConfigGroup 2 }

        hpnicfIfQoSQSWeightEntry OBJECT-TYPE
            SYNTAX HpnicfIfQoSQSWeightEntry
            MAX-ACCESS not-accessible
            STATUS current
            DESCRIPTION
                "Queue schedule weight configuration information entry."
            INDEX { ifIndex, hpnicfIfQoSQueueID }
            ::= { hpnicfIfQoSQSWeightTable 1 }

        HpnicfIfQoSQSWeightEntry ::=
            SEQUENCE
            {
                hpnicfIfQoSQueueID
                    Integer32,
                hpnicfIfQoSQueueGroupType
                    INTEGER,
                hpnicfIfQoSQSType
                    INTEGER,
                hpnicfIfQoSQSValue
                    Integer32,
                hpnicfIfQoSQSMaxDelay
                    Integer32,
                hpnicfIfQoSQSMinBandwidth
                    Integer32,
                hpnicfIfQoSQSMinBandwidthPercent
                    Unsigned32
            }

        hpnicfIfQoSQueueID OBJECT-TYPE
            SYNTAX Integer32
            MAX-ACCESS not-accessible
            STATUS current
            DESCRIPTION
                "Queue ID"
            ::= { hpnicfIfQoSQSWeightEntry 1 }

        hpnicfIfQoSQueueGroupType OBJECT-TYPE
            SYNTAX INTEGER
            {
                group0(1),
                group1(2),
                group2(3)
            }
            MAX-ACCESS read-write
            STATUS current
            DESCRIPTION
                "Group type of WRR and WFQ."
            ::= { hpnicfIfQoSQSWeightEntry 2 }

        hpnicfIfQoSQSType OBJECT-TYPE
            SYNTAX INTEGER
            {
                weight(1),
                byte-count(2)
            }
            MAX-ACCESS read-write
            STATUS current
            DESCRIPTION
                "Schedule type."
            ::= { hpnicfIfQoSQSWeightEntry 3 }

        hpnicfIfQoSQSValue OBJECT-TYPE
            SYNTAX Integer32
            MAX-ACCESS read-write
            STATUS current
            DESCRIPTION
                "Schedule value."
            ::= { hpnicfIfQoSQSWeightEntry 4 }

        hpnicfIfQoSQSMaxDelay OBJECT-TYPE
            SYNTAX Integer32
            MAX-ACCESS read-write
            STATUS current
            DESCRIPTION
                "Max delay."
            DEFVAL { 9 }
            ::= { hpnicfIfQoSQSWeightEntry 5 }

        hpnicfIfQoSQSMinBandwidth OBJECT-TYPE
            SYNTAX Integer32
            MAX-ACCESS read-write
            STATUS current
            DESCRIPTION
                "Min bandwidth.  Unit: kbps."
            ::= { hpnicfIfQoSQSWeightEntry 6 }

        hpnicfIfQoSQSMinBandwidthPercent OBJECT-TYPE
            SYNTAX Unsigned32  (0..100 | 255)
            MAX-ACCESS read-write
            STATUS current
            DESCRIPTION
                "Percent of min bandwidth.  Unit: %.
                 The value is 255 when the schedule mode of the queue is strict queuing.
                "
            ::= { hpnicfIfQoSQSWeightEntry 7 }

--
-- nodes of hpnicfIfQoSHardwareQueueRunInfoGroup
--
        hpnicfIfQoSHardwareQueueRunInfoGroup OBJECT IDENTIFIER ::= { hpnicfIfQoSHardwareQueueObjects 2 }

        hpnicfIfQoSHardwareQueueRunInfoTable OBJECT-TYPE
            SYNTAX SEQUENCE OF HpnicfIfQoSHardwareQueueRunInfoEntry
            MAX-ACCESS not-accessible
            STATUS current
            DESCRIPTION
                "A table of queue statistic information."
            ::= { hpnicfIfQoSHardwareQueueRunInfoGroup 1 }

        hpnicfIfQoSHardwareQueueRunInfoEntry OBJECT-TYPE
            SYNTAX HpnicfIfQoSHardwareQueueRunInfoEntry
            MAX-ACCESS not-accessible
            STATUS current
            DESCRIPTION
                "Queue statistic information entry."
            INDEX { ifIndex, hpnicfIfQoSQueueID }
            ::= { hpnicfIfQoSHardwareQueueRunInfoTable 1 }

        HpnicfIfQoSHardwareQueueRunInfoEntry ::=
            SEQUENCE
            {
                hpnicfIfQoSPassPackets
                    Counter64,
                hpnicfIfQoSDropPackets
                    Counter64,
                hpnicfIfQoSPassBytes
                    Counter64,
                hpnicfIfQoSPassPPS
                    Unsigned32,
                hpnicfIfQoSPassBPS
                    Unsigned32,
                hpnicfIfQoSDropBytes
                    Counter64,
                hpnicfIfQoSQueueLengthInPkts
                    Unsigned32,
                hpnicfIfQoSQueueLengthInBytes
                    Unsigned32,
                hpnicfIfQoSCurQueuePkts
                    Unsigned32,
                hpnicfIfQoSCurQueueBytes
                    Unsigned32,
                hpnicfIfQoSCurQueuePPS
                    Unsigned32,
                hpnicfIfQoSCurQueueBPS
                    Unsigned32,
                hpnicfIfQoSTailDropPkts
                    Counter64,
                hpnicfIfQoSTailDropBytes
                    Counter64,
                hpnicfIfQoSTailDropPPS
                    Unsigned32,
                hpnicfIfQoSTailDropBPS
                    Unsigned32,
                hpnicfIfQoSWredDropPkts
                    Counter64,
                hpnicfIfQoSWredDropBytes
                    Counter64,
                hpnicfIfQoSWredDropPPS
                    Unsigned32,
                hpnicfIfQoSWredDropBPS
                    Unsigned32
            }

        hpnicfIfQoSPassPackets OBJECT-TYPE
            SYNTAX Counter64
            MAX-ACCESS read-only
            STATUS current
            DESCRIPTION
                "The number of forwarded packets."
            ::= { hpnicfIfQoSHardwareQueueRunInfoEntry 1 }

        hpnicfIfQoSDropPackets OBJECT-TYPE
            SYNTAX Counter64
            MAX-ACCESS read-only
            STATUS current
            DESCRIPTION
                "The number of dropped packets."
            ::= { hpnicfIfQoSHardwareQueueRunInfoEntry 2 }

        hpnicfIfQoSPassBytes OBJECT-TYPE
            SYNTAX Counter64
            MAX-ACCESS read-only
            STATUS current
            DESCRIPTION
                "The bytes of forwarded packets."
            ::= { hpnicfIfQoSHardwareQueueRunInfoEntry 3 }

        hpnicfIfQoSPassPPS OBJECT-TYPE
            SYNTAX Unsigned32
            MAX-ACCESS read-only
            STATUS current
            DESCRIPTION
                "The PPS of forwarded packets.  PPS: packets per second."
            ::= { hpnicfIfQoSHardwareQueueRunInfoEntry 4 }

        hpnicfIfQoSPassBPS OBJECT-TYPE
            SYNTAX Unsigned32
            MAX-ACCESS read-only
            STATUS current
            DESCRIPTION
                "The BPS of forwarded packets.  BPS: bytes per second."
            ::= { hpnicfIfQoSHardwareQueueRunInfoEntry 5 }

        hpnicfIfQoSDropBytes OBJECT-TYPE
            SYNTAX Counter64
            MAX-ACCESS read-only
            STATUS current
            DESCRIPTION
                "The bytes of dropped packets."
            ::= { hpnicfIfQoSHardwareQueueRunInfoEntry 6 }

        hpnicfIfQoSQueueLengthInPkts OBJECT-TYPE
            SYNTAX Unsigned32
            MAX-ACCESS read-only
            STATUS current
            DESCRIPTION
                "The max number of packets which the queue can hold."
            ::= { hpnicfIfQoSHardwareQueueRunInfoEntry 7 }

        hpnicfIfQoSQueueLengthInBytes OBJECT-TYPE
            SYNTAX Unsigned32
            MAX-ACCESS read-only
            STATUS current
            DESCRIPTION
                "The max bytes of packets which the queue can hold."
            ::= { hpnicfIfQoSHardwareQueueRunInfoEntry 8 }

        hpnicfIfQoSCurQueuePkts OBJECT-TYPE
            SYNTAX Unsigned32
            MAX-ACCESS read-only
            STATUS current
            DESCRIPTION
                "The number of packets in the current queue."
            ::= { hpnicfIfQoSHardwareQueueRunInfoEntry 9 }

        hpnicfIfQoSCurQueueBytes OBJECT-TYPE
            SYNTAX Unsigned32
            MAX-ACCESS read-only
            STATUS current
            DESCRIPTION
                "The bytes of packets in the current queue."
            ::= { hpnicfIfQoSHardwareQueueRunInfoEntry 10 }

        hpnicfIfQoSCurQueuePPS OBJECT-TYPE
            SYNTAX Unsigned32
            MAX-ACCESS read-only
            STATUS current
            DESCRIPTION
                "The PPS of packets in the current queue."
            ::= { hpnicfIfQoSHardwareQueueRunInfoEntry 11 }

        hpnicfIfQoSCurQueueBPS OBJECT-TYPE
            SYNTAX Unsigned32
            MAX-ACCESS read-only
            STATUS current
            DESCRIPTION
                "The BPS of packets in the current queue."
            ::= { hpnicfIfQoSHardwareQueueRunInfoEntry 12 }

        hpnicfIfQoSTailDropPkts OBJECT-TYPE
            SYNTAX Counter64
            MAX-ACCESS read-only
            STATUS current
            DESCRIPTION
                "The number of packets dropped by tail dropping."
            ::= { hpnicfIfQoSHardwareQueueRunInfoEntry 13 }

        hpnicfIfQoSTailDropBytes OBJECT-TYPE
            SYNTAX Counter64
            MAX-ACCESS read-only
            STATUS current
            DESCRIPTION
                "The bytes of packets dropped by tail dropping."
            ::= { hpnicfIfQoSHardwareQueueRunInfoEntry 14 }

        hpnicfIfQoSTailDropPPS OBJECT-TYPE
            SYNTAX Unsigned32
            MAX-ACCESS read-only
            STATUS current
            DESCRIPTION
                "The PPS of packets dropped by tail dropping."
            ::= { hpnicfIfQoSHardwareQueueRunInfoEntry 15 }

        hpnicfIfQoSTailDropBPS OBJECT-TYPE
            SYNTAX Unsigned32
            MAX-ACCESS read-only
            STATUS current
            DESCRIPTION
                "The BPS of packets dropped by tail dropping."
            ::= { hpnicfIfQoSHardwareQueueRunInfoEntry 16 }

        hpnicfIfQoSWredDropPkts OBJECT-TYPE
            SYNTAX Counter64
            MAX-ACCESS read-only
            STATUS current
            DESCRIPTION
                "The number of packets dropped by WRED."
            ::= { hpnicfIfQoSHardwareQueueRunInfoEntry 17 }

        hpnicfIfQoSWredDropBytes OBJECT-TYPE
            SYNTAX Counter64
            MAX-ACCESS read-only
            STATUS current
            DESCRIPTION
                "The bytes of packets dropped by WRED."
            ::= { hpnicfIfQoSHardwareQueueRunInfoEntry 18 }

        hpnicfIfQoSWredDropPPS OBJECT-TYPE
            SYNTAX Unsigned32
            MAX-ACCESS read-only
            STATUS current
            DESCRIPTION
                "The PPS of packets dropped by WRED."
            ::= { hpnicfIfQoSHardwareQueueRunInfoEntry 19 }

        hpnicfIfQoSWredDropBPS OBJECT-TYPE
            SYNTAX Unsigned32
            MAX-ACCESS read-only
            STATUS current
            DESCRIPTION
                "The BPS of packets dropped by WRED."
            ::= { hpnicfIfQoSHardwareQueueRunInfoEntry 20 }

--
-- nodes of hpnicfIfQoSHQueueTcpRunInfoTable
--

        hpnicfIfQoSHQueueTcpRunInfoTable OBJECT-TYPE
            SYNTAX SEQUENCE OF HpnicfIfQoSHQueueTcpRunInfoEntry
            MAX-ACCESS not-accessible
            STATUS current
            DESCRIPTION
                "A table of queue statistic information
                 about TCP and non-TCP packets."
            ::= { hpnicfIfQoSHardwareQueueRunInfoGroup 2 }

        hpnicfIfQoSHQueueTcpRunInfoEntry OBJECT-TYPE
            SYNTAX HpnicfIfQoSHQueueTcpRunInfoEntry
            MAX-ACCESS not-accessible
            STATUS current
            DESCRIPTION
                "Queue statistic information entry
                 about TCP and non-TCP packets."
            INDEX { ifIndex, hpnicfIfQoSQueueID }
            ::= { hpnicfIfQoSHQueueTcpRunInfoTable 1 }

        HpnicfIfQoSHQueueTcpRunInfoEntry ::=
            SEQUENCE
            {
                hpnicfIfQoSWredDropLPreNTcpPkts
                    Counter64,
                hpnicfIfQoSWredDropLPreNTcpBytes
                    Counter64,
                hpnicfIfQoSWredDropLPreNTcpPPS
                    Unsigned32,
                hpnicfIfQoSWredDropLPreNTcpBPS
                    Unsigned32,
                hpnicfIfQoSWredDropLPreTcpPkts
                    Counter64,
                hpnicfIfQoSWredDropLPreTcpBytes
                    Counter64,
                hpnicfIfQoSWredDropLPreTcpPPS
                    Unsigned32,
                hpnicfIfQoSWredDropLPreTcpBPS
                    Unsigned32,
                hpnicfIfQoSWredDropHPreNTcpPkts
                    Counter64,
                hpnicfIfQoSWredDropHPreNTcpBytes
                    Counter64,
                hpnicfIfQoSWredDropHPreNTcpPPS
                    Unsigned32,
                hpnicfIfQoSWredDropHPreNTcpBPS
                    Unsigned32,
                hpnicfIfQoSWredDropHPreTcpPkts
                    Counter64,
                hpnicfIfQoSWredDropHPreTcpBytes
                    Counter64,
                hpnicfIfQoSWredDropHPreTcpPPS
                    Unsigned32,
                hpnicfIfQoSWredDropHPreTcpBPS
                    Unsigned32
            }

        hpnicfIfQoSWredDropLPreNTcpPkts OBJECT-TYPE
            SYNTAX Counter64
            MAX-ACCESS read-only
            STATUS current
            DESCRIPTION
                "The number of low-precedence non-TCP packets dropped by WRED."
            ::= { hpnicfIfQoSHQueueTcpRunInfoEntry 1 }

        hpnicfIfQoSWredDropLPreNTcpBytes OBJECT-TYPE
            SYNTAX Counter64
            MAX-ACCESS read-only
            STATUS current
            DESCRIPTION
                "The bytes of low-precedence non-TCP packets dropped by WRED."
            ::= { hpnicfIfQoSHQueueTcpRunInfoEntry 2 }

        hpnicfIfQoSWredDropLPreNTcpPPS OBJECT-TYPE
            SYNTAX Unsigned32
            MAX-ACCESS read-only
            STATUS current
            DESCRIPTION
                "The PPS of low-precedence non-TCP packets dropped by WRED.
                 PPS: packets per second."
            ::= { hpnicfIfQoSHQueueTcpRunInfoEntry 3 }

        hpnicfIfQoSWredDropLPreNTcpBPS OBJECT-TYPE
            SYNTAX Unsigned32
            MAX-ACCESS read-only
            STATUS current
            DESCRIPTION
                "The BPS of low-precedence non-TCP packets dropped by WRED.
                 BPS: bytes per second."
            ::= { hpnicfIfQoSHQueueTcpRunInfoEntry 4 }

        hpnicfIfQoSWredDropLPreTcpPkts OBJECT-TYPE
            SYNTAX Counter64
            MAX-ACCESS read-only
            STATUS current
            DESCRIPTION
                "The number of low-precedence TCP packets dropped by WRED."
            ::= { hpnicfIfQoSHQueueTcpRunInfoEntry 5 }

        hpnicfIfQoSWredDropLPreTcpBytes OBJECT-TYPE
            SYNTAX Counter64
            MAX-ACCESS read-only
            STATUS current
            DESCRIPTION
                "The bytes of low-precedence TCP packets dropped by WRED."
            ::= { hpnicfIfQoSHQueueTcpRunInfoEntry 6 }

        hpnicfIfQoSWredDropLPreTcpPPS OBJECT-TYPE
            SYNTAX Unsigned32
            MAX-ACCESS read-only
            STATUS current
            DESCRIPTION
                "The PPS of low-precedence TCP packets dropped by WRED."
            ::= { hpnicfIfQoSHQueueTcpRunInfoEntry 7 }

        hpnicfIfQoSWredDropLPreTcpBPS OBJECT-TYPE
            SYNTAX Unsigned32
            MAX-ACCESS read-only
            STATUS current
            DESCRIPTION
                "The BPS of low-precedence TCP packets dropped by WRED."
            ::= { hpnicfIfQoSHQueueTcpRunInfoEntry 8 }

        hpnicfIfQoSWredDropHPreNTcpPkts OBJECT-TYPE
            SYNTAX Counter64
            MAX-ACCESS read-only
            STATUS current
            DESCRIPTION
                "The number of high-precedence non-TCP packets dropped by WRED."
            ::= { hpnicfIfQoSHQueueTcpRunInfoEntry 9 }

        hpnicfIfQoSWredDropHPreNTcpBytes OBJECT-TYPE
            SYNTAX Counter64
            MAX-ACCESS read-only
            STATUS current
            DESCRIPTION
                "The bytes of high-precedence non-TCP packets dropped by WRED."
            ::= { hpnicfIfQoSHQueueTcpRunInfoEntry 10 }

        hpnicfIfQoSWredDropHPreNTcpPPS OBJECT-TYPE
            SYNTAX Unsigned32
            MAX-ACCESS read-only
            STATUS current
            DESCRIPTION
                "The PPS of high-precedence non-TCP packets dropped by WRED."
            ::= { hpnicfIfQoSHQueueTcpRunInfoEntry 11 }

        hpnicfIfQoSWredDropHPreNTcpBPS OBJECT-TYPE
            SYNTAX Unsigned32
            MAX-ACCESS read-only
            STATUS current
            DESCRIPTION
                "The BPS of high-precedence non-TCP packets dropped by WRED."
            ::= { hpnicfIfQoSHQueueTcpRunInfoEntry 12 }

        hpnicfIfQoSWredDropHPreTcpPkts OBJECT-TYPE
            SYNTAX Counter64
            MAX-ACCESS read-only
            STATUS current
            DESCRIPTION
                "The number of high-precedence TCP packets dropped by WRED."
            ::= { hpnicfIfQoSHQueueTcpRunInfoEntry 13 }

        hpnicfIfQoSWredDropHPreTcpBytes OBJECT-TYPE
            SYNTAX Counter64
            MAX-ACCESS read-only
            STATUS current
            DESCRIPTION
                "The bytes of high-precedence TCP packets dropped by WRED."
            ::= { hpnicfIfQoSHQueueTcpRunInfoEntry 14 }

        hpnicfIfQoSWredDropHPreTcpPPS OBJECT-TYPE
            SYNTAX Unsigned32
            MAX-ACCESS read-only
            STATUS current
            DESCRIPTION
                "The PPS of high-precedence TCP packets dropped by WRED."
            ::= { hpnicfIfQoSHQueueTcpRunInfoEntry 15 }

        hpnicfIfQoSWredDropHPreTcpBPS OBJECT-TYPE
            SYNTAX Unsigned32
            MAX-ACCESS read-only
            STATUS current
            DESCRIPTION
                "The BPS of high-precedence TCP packets dropped by WRED."
            ::= { hpnicfIfQoSHQueueTcpRunInfoEntry 16 }

--
-- nodes of hpnicfIfQoSSoftwareQueueObjects
--
        hpnicfIfQoSSoftwareQueueObjects OBJECT IDENTIFIER ::= { hpnicfIfQos2 2 }

--
-- nodes of hpnicfIfQoSFIFOObject
--
        hpnicfIfQoSFIFOObject OBJECT IDENTIFIER ::= { hpnicfIfQoSSoftwareQueueObjects 1 }

        hpnicfIfQoSFIFOConfigTable OBJECT-TYPE
            SYNTAX SEQUENCE OF HpnicfIfQoSFIFOConfigEntry
            MAX-ACCESS not-accessible
            STATUS current
            DESCRIPTION
                "A table of FIFO queue information."
            ::= { hpnicfIfQoSFIFOObject 1 }

        hpnicfIfQoSFIFOConfigEntry OBJECT-TYPE
            SYNTAX HpnicfIfQoSFIFOConfigEntry
            MAX-ACCESS not-accessible
            STATUS current
            DESCRIPTION
                "FIFO queue information entry."
            INDEX { ifIndex }
            ::= { hpnicfIfQoSFIFOConfigTable 1 }

        HpnicfIfQoSFIFOConfigEntry ::=
            SEQUENCE
            {
                hpnicfIfQoSFIFOMaxQueueLen
                    Integer32
            }

        hpnicfIfQoSFIFOMaxQueueLen OBJECT-TYPE
            SYNTAX Integer32
            MAX-ACCESS read-write
            STATUS current
            DESCRIPTION
                "The maximum length of FIFO queue."
            ::= { hpnicfIfQoSFIFOConfigEntry 1 }

--
-- nodes of hpnicfIfQoSFifoRunfoTable
--

        hpnicfIfQoSFIFORunInfoTable OBJECT-TYPE
            SYNTAX SEQUENCE OF HpnicfIfQoSFIFORunInfoEntry
            MAX-ACCESS not-accessible
            STATUS current
            DESCRIPTION
                "A table of FIFO queue statistic information."
            ::= { hpnicfIfQoSFIFOObject 2 }

        hpnicfIfQoSFIFORunInfoEntry OBJECT-TYPE
            SYNTAX HpnicfIfQoSFIFORunInfoEntry
            MAX-ACCESS not-accessible
            STATUS current
            DESCRIPTION
                "FIFO queue statistic information entry."
            INDEX { ifIndex }
            ::= { hpnicfIfQoSFIFORunInfoTable 1 }

        HpnicfIfQoSFIFORunInfoEntry ::=
            SEQUENCE
            {
                hpnicfIfQoSFIFOSize
                    Integer32,
                hpnicfIfQoSFIFODiscardPackets
                    Counter64
            }

        hpnicfIfQoSFIFOSize OBJECT-TYPE
            SYNTAX Integer32
            MAX-ACCESS read-only
            STATUS current
            DESCRIPTION
                "The number of packet in FIFO queue."
            ::= { hpnicfIfQoSFIFORunInfoEntry 1 }

        hpnicfIfQoSFIFODiscardPackets OBJECT-TYPE
            SYNTAX Counter64
            MAX-ACCESS read-only
            STATUS current
            DESCRIPTION
                "The number of discard packet."
            ::= { hpnicfIfQoSFIFORunInfoEntry 2 }

--
-- nodes of
--
        hpnicfIfQoSPQObject OBJECT IDENTIFIER ::= { hpnicfIfQoSSoftwareQueueObjects 2 }

        hpnicfIfQoSPQConfigGroup OBJECT IDENTIFIER ::= { hpnicfIfQoSPQObject 1 }

        hpnicfIfQoSPQDefaultTable OBJECT-TYPE
            SYNTAX SEQUENCE OF HpnicfIfQoSPQDefaultEntry
            MAX-ACCESS not-accessible
            STATUS current
            DESCRIPTION
                "A table of priority queue default configuration information."
            ::= { hpnicfIfQoSPQConfigGroup 1 }

        hpnicfIfQoSPQDefaultEntry OBJECT-TYPE
            SYNTAX HpnicfIfQoSPQDefaultEntry
            MAX-ACCESS not-accessible
            STATUS current
            DESCRIPTION
                "Priority queue default configuration information entry."
            INDEX { hpnicfIfQoSPQListNumber }
            ::= { hpnicfIfQoSPQDefaultTable 1 }

        HpnicfIfQoSPQDefaultEntry ::=
            SEQUENCE
            {
                hpnicfIfQoSPQListNumber
                    Integer32,
                hpnicfIfQoSPQDefaultQueueType
                    PriorityQueue
            }

        hpnicfIfQoSPQListNumber OBJECT-TYPE
            SYNTAX Integer32 (1..16)
            MAX-ACCESS not-accessible
            STATUS current
            DESCRIPTION
                "Priority queue list number."
            ::= { hpnicfIfQoSPQDefaultEntry 1 }

        hpnicfIfQoSPQDefaultQueueType OBJECT-TYPE
            SYNTAX PriorityQueue
            MAX-ACCESS read-write
            STATUS current
            DESCRIPTION
                "Specify priority queue that packets put into by default."
            ::= { hpnicfIfQoSPQDefaultEntry 2 }
--
-- nods of hpnicfIfQoSPQQueueLengthTable
--
        hpnicfIfQoSPQQueueLengthTable OBJECT-TYPE
            SYNTAX SEQUENCE OF HpnicfIfQoSPQQueueLengthEntry
            MAX-ACCESS not-accessible
            STATUS current
            DESCRIPTION
                "A table of queue length of priority queue configuration information."
            ::= { hpnicfIfQoSPQConfigGroup 2 }

        hpnicfIfQoSPQQueueLengthEntry OBJECT-TYPE
            SYNTAX HpnicfIfQoSPQQueueLengthEntry
            MAX-ACCESS not-accessible
            STATUS current
            DESCRIPTION
                "Queue length of priority queue configuration information entry."
            INDEX { hpnicfIfQoSPQListNumber, hpnicfIfQoSPQQueueLengthType }
            ::= { hpnicfIfQoSPQQueueLengthTable 1 }

        HpnicfIfQoSPQQueueLengthEntry ::=
            SEQUENCE
            {
                hpnicfIfQoSPQQueueLengthType
                    PriorityQueue,
                hpnicfIfQoSPQQueueLengthValue
                    Integer32
            }

        hpnicfIfQoSPQQueueLengthType OBJECT-TYPE
            SYNTAX PriorityQueue
            MAX-ACCESS not-accessible
            STATUS current
            DESCRIPTION
                "Type of priority queue."
            ::= { hpnicfIfQoSPQQueueLengthEntry 1 }

        hpnicfIfQoSPQQueueLengthValue OBJECT-TYPE
            SYNTAX Integer32 (1..1024)
            MAX-ACCESS read-write
            STATUS current
            DESCRIPTION
                "The size of priority queue."
            ::= { hpnicfIfQoSPQQueueLengthEntry 2 }

--
-- nodes of hpnicfIfQoSPQClassRuleTable
--
        hpnicfIfQoSPQClassRuleTable OBJECT-TYPE
            SYNTAX SEQUENCE OF HpnicfIfQoSPQClassRuleEntry
            MAX-ACCESS not-accessible
            STATUS current
            DESCRIPTION
                "A table of class rule of priority queue information."
            ::= { hpnicfIfQoSPQConfigGroup 3 }

        hpnicfIfQoSPQClassRuleEntry OBJECT-TYPE
            SYNTAX HpnicfIfQoSPQClassRuleEntry
            MAX-ACCESS not-accessible
            STATUS current
            DESCRIPTION
                "A table of class rule of priority queue information."
            INDEX { hpnicfIfQoSPQListNumber,
                    hpnicfIfQoSPQClassRuleType,
                    hpnicfIfQoSPQClassRuleValue }
            ::= { hpnicfIfQoSPQClassRuleTable 1 }

        HpnicfIfQoSPQClassRuleEntry ::=
            SEQUENCE
            {
                hpnicfIfQoSPQClassRuleType
                    INTEGER,
                hpnicfIfQoSPQClassRuleValue
                    Integer32,
                hpnicfIfQoSPQClassRuleQueueType
                    PriorityQueue,
                hpnicfIfQoSPQClassRowStatus
                    RowStatus
            }

        hpnicfIfQoSPQClassRuleType OBJECT-TYPE
            SYNTAX INTEGER
            {
                interface(1),
                ipv4acl(2),
                ipv6acl(3),
                fragments(4),
                greater-than(5),
                less-than(6),
                tcp(7),
                udp(8),
                ipall(9),
                mpls(10)
            }
            MAX-ACCESS not-accessible
            STATUS current
            DESCRIPTION
                "Type of class rule.
                'ipall' means all ip packets."
            ::= { hpnicfIfQoSPQClassRuleEntry 1 }

        hpnicfIfQoSPQClassRuleValue OBJECT-TYPE
            SYNTAX Integer32
            MAX-ACCESS not-accessible
            STATUS current
            DESCRIPTION
                "Value of class rule.
                 interface : ifIndex
                 ipv4acl : 2000..3999
                 ipv6acl : 2000..3999, 10000..42767
                 greater-than : 0..65535
                 less-than : 0..65535
                 tcp : 0..65535
                 udp : 0..65535
                 mpls(exp-mask) : 1..255
                 other types: 0
                "
            ::= { hpnicfIfQoSPQClassRuleEntry 2 }

        hpnicfIfQoSPQClassRuleQueueType OBJECT-TYPE
            SYNTAX PriorityQueue
            MAX-ACCESS read-create
            STATUS current
            DESCRIPTION
                "Specify the queue for matched packets."
            ::= { hpnicfIfQoSPQClassRuleEntry 3 }

        hpnicfIfQoSPQClassRowStatus OBJECT-TYPE
            SYNTAX RowStatus
            MAX-ACCESS read-create
            STATUS current
            DESCRIPTION
                "RowStatus."
            ::= { hpnicfIfQoSPQClassRuleEntry 4 }
--
-- nodes of hpnicfIfQoSPQApplyTable
--
        hpnicfIfQoSPQApplyTable OBJECT-TYPE
            SYNTAX SEQUENCE OF HpnicfIfQoSPQApplyEntry
            MAX-ACCESS not-accessible
            STATUS current
            DESCRIPTION
                "A table of priority queue instance."
            ::= { hpnicfIfQoSPQConfigGroup 4 }

        hpnicfIfQoSPQApplyEntry OBJECT-TYPE
            SYNTAX HpnicfIfQoSPQApplyEntry
            MAX-ACCESS not-accessible
            STATUS current
            DESCRIPTION
                "Priority queue instance information."
            INDEX { ifIndex }
            ::= { hpnicfIfQoSPQApplyTable 1 }

        HpnicfIfQoSPQApplyEntry ::=
            SEQUENCE
            {
                hpnicfIfQoSPQApplyListNumber
                    Integer32,
                hpnicfIfQoSPQApplyRowStatus
                    RowStatus
            }

        hpnicfIfQoSPQApplyListNumber OBJECT-TYPE
            SYNTAX Integer32 (1..16)
            MAX-ACCESS read-create
            STATUS current
            DESCRIPTION
                "Priority queue list number."
            ::= { hpnicfIfQoSPQApplyEntry 1 }

        hpnicfIfQoSPQApplyRowStatus OBJECT-TYPE
            SYNTAX RowStatus
            MAX-ACCESS read-create
            STATUS current
            DESCRIPTION
                "RowStatus."
            ::= { hpnicfIfQoSPQApplyEntry 2 }

--
-- Nodes of hpnicfIfQoSPQRunInfoGroup
--
        hpnicfIfQoSPQRunInfoGroup OBJECT IDENTIFIER ::= { hpnicfIfQoSPQObject 2 }
--
-- nodes of hpnicfIfQoSPQRunInfoTable
--
        hpnicfIfQoSPQRunInfoTable OBJECT-TYPE
            SYNTAX SEQUENCE OF HpnicfIfQoSPQRunInfoEntry
            MAX-ACCESS not-accessible
            STATUS current
            DESCRIPTION
                "A table of priority queue statistic information."
            ::= { hpnicfIfQoSPQRunInfoGroup 1 }

        hpnicfIfQoSPQRunInfoEntry OBJECT-TYPE
            SYNTAX HpnicfIfQoSPQRunInfoEntry
            MAX-ACCESS not-accessible
            STATUS current
            DESCRIPTION
                "Priority queue statistic information entry."
            INDEX { ifIndex, hpnicfIfQoSPQType }
            ::= { hpnicfIfQoSPQRunInfoTable 1 }

        HpnicfIfQoSPQRunInfoEntry ::=
            SEQUENCE
            {
                hpnicfIfQoSPQType
                    PriorityQueue,
                hpnicfIfQoSPQSize
                    Integer32,
                hpnicfIfQoSPQLength
                    Integer32,
                hpnicfIfQoSPQDiscardPackets
                    Counter64
            }

        hpnicfIfQoSPQType OBJECT-TYPE
            SYNTAX PriorityQueue
            MAX-ACCESS not-accessible
            STATUS current
            DESCRIPTION
                "The type of priority queue."
            ::= { hpnicfIfQoSPQRunInfoEntry 1 }

        hpnicfIfQoSPQSize OBJECT-TYPE
            SYNTAX Integer32
            MAX-ACCESS read-only
            STATUS current
            DESCRIPTION
                "The number of packets in the priority queue."
            ::= { hpnicfIfQoSPQRunInfoEntry 2 }

        hpnicfIfQoSPQLength OBJECT-TYPE
            SYNTAX Integer32
            MAX-ACCESS read-only
            STATUS current
            DESCRIPTION
                "The maximum length of priority queue."
            ::= { hpnicfIfQoSPQRunInfoEntry 3 }

        hpnicfIfQoSPQDiscardPackets    OBJECT-TYPE
            SYNTAX Counter64
            MAX-ACCESS read-only
            STATUS current
            DESCRIPTION
                "The packet number of priority queue discard."
            ::= { hpnicfIfQoSPQRunInfoEntry 4 }
--
-- nodes of hpnicfIfQoSCQObject

        hpnicfIfQoSCQObject OBJECT IDENTIFIER ::= { hpnicfIfQoSSoftwareQueueObjects 3 }

        hpnicfIfQoSCQConfigGroup OBJECT IDENTIFIER ::= { hpnicfIfQoSCQObject 1 }

--
-- nodes of hpnicfIfQoSCQDefaultTable
--
        hpnicfIfQoSCQDefaultTable OBJECT-TYPE
            SYNTAX SEQUENCE OF HpnicfIfQoSCQDefaultEntry
            MAX-ACCESS not-accessible
            STATUS current
            DESCRIPTION
                "A table of custom queue default configuration information."
            ::= { hpnicfIfQoSCQConfigGroup 1 }

        hpnicfIfQoSCQDefaultEntry OBJECT-TYPE
            SYNTAX HpnicfIfQoSCQDefaultEntry
            MAX-ACCESS not-accessible
            STATUS current
            DESCRIPTION
                "Custom queue default configuration information entry."
            INDEX { hpnicfIfQoSCQListNumber }
            ::= { hpnicfIfQoSCQDefaultTable 1 }

        HpnicfIfQoSCQDefaultEntry ::=
            SEQUENCE
            {
                hpnicfIfQoSCQListNumber
                    Integer32,
                hpnicfIfQoSCQDefaultQueueID
                    Integer32
            }

        hpnicfIfQoSCQListNumber OBJECT-TYPE
            SYNTAX Integer32 (1..16)
            MAX-ACCESS not-accessible
            STATUS current
            DESCRIPTION
                "Custom queue list number."
            ::= { hpnicfIfQoSCQDefaultEntry 1 }

        hpnicfIfQoSCQDefaultQueueID OBJECT-TYPE
            SYNTAX Integer32 (0..16)
            MAX-ACCESS read-write
            STATUS current
            DESCRIPTION
                "Default queue ID."
            DEFVAL { 1 }
            ::= { hpnicfIfQoSCQDefaultEntry 2 }
--
-- nods of hpnicfIfQoSCQQueueLengthTable
--
        hpnicfIfQoSCQQueueLengthTable OBJECT-TYPE
            SYNTAX SEQUENCE OF HpnicfIfQoSCQQueueLengthEntry
            MAX-ACCESS not-accessible
            STATUS current
            DESCRIPTION
                "A table of queue length of custom queue configuration information."
            ::= { hpnicfIfQoSCQConfigGroup 2 }

        hpnicfIfQoSCQQueueLengthEntry OBJECT-TYPE
            SYNTAX HpnicfIfQoSCQQueueLengthEntry
            MAX-ACCESS not-accessible
            STATUS current
            DESCRIPTION
                "Queue length of custom queue configuration information entry."
            INDEX { hpnicfIfQoSCQListNumber, hpnicfIfQoSCQQueueID }
            ::= { hpnicfIfQoSCQQueueLengthTable 1 }

        HpnicfIfQoSCQQueueLengthEntry ::=
            SEQUENCE
            {
                hpnicfIfQoSCQQueueID
                    Integer32,
                hpnicfIfQoSCQQueueLength
                    Integer32,
                hpnicfIfQoSCQQueueServing
                    Integer32
            }

        hpnicfIfQoSCQQueueID OBJECT-TYPE
            SYNTAX Integer32 (1..16)
            MAX-ACCESS not-accessible
            STATUS current
            DESCRIPTION
                "Custom queue index."
            ::= { hpnicfIfQoSCQQueueLengthEntry 1 }

        hpnicfIfQoSCQQueueLength OBJECT-TYPE
            SYNTAX Integer32 (1..1024)
            MAX-ACCESS read-write
            STATUS current
            DESCRIPTION
                "The size of custom queue."
            DEFVAL { 20 }
            ::= { hpnicfIfQoSCQQueueLengthEntry 2 }

        hpnicfIfQoSCQQueueServing OBJECT-TYPE
            SYNTAX Integer32
            MAX-ACCESS read-write
            STATUS current
            DESCRIPTION
                "The maximum bytes that the specified queue can transmit in each turn."
            DEFVAL { 1500 }
            ::= { hpnicfIfQoSCQQueueLengthEntry 3 }

--
-- nodes of hpnicfIfQoSCQClassRuleTable
--
        hpnicfIfQoSCQClassRuleTable OBJECT-TYPE
            SYNTAX SEQUENCE OF HpnicfIfQoSCQClassRuleEntry
            MAX-ACCESS not-accessible
            STATUS current
            DESCRIPTION
                "A table of class rule of custom queue information."
            ::= { hpnicfIfQoSCQConfigGroup 3 }

        hpnicfIfQoSCQClassRuleEntry OBJECT-TYPE
            SYNTAX HpnicfIfQoSCQClassRuleEntry
            MAX-ACCESS not-accessible
            STATUS current
            DESCRIPTION
                "A table of class rule of custom queue information."
            INDEX { hpnicfIfQoSCQListNumber,
                    hpnicfIfQoSCQClassRuleType,
                    hpnicfIfQoSCQClassRuleValue }
            ::= { hpnicfIfQoSCQClassRuleTable 1 }

        HpnicfIfQoSCQClassRuleEntry ::=
            SEQUENCE
            {
                hpnicfIfQoSCQClassRuleType
                    INTEGER,
                hpnicfIfQoSCQClassRuleValue
                    Integer32,
                hpnicfIfQoSCQClassRuleQueueID
                    Integer32,
                hpnicfIfQoSCQClassRowStatus
                    RowStatus
            }

        hpnicfIfQoSCQClassRuleType OBJECT-TYPE
            SYNTAX INTEGER
            {
                interface(1),
                ipv4acl(2),
                ipv6acl(3),
                fragments(4),
                greater-than(5),
                less-than(6),
                tcp(7),
                udp(8),
                ipall(9),
                mpls(10)
            }
            MAX-ACCESS not-accessible
            STATUS current
            DESCRIPTION
                "Type of class rule.
                'ipall' means all ip packets."
            ::= { hpnicfIfQoSCQClassRuleEntry 1 }

        hpnicfIfQoSCQClassRuleValue OBJECT-TYPE
            SYNTAX Integer32
            MAX-ACCESS not-accessible
            STATUS current
            DESCRIPTION
                "Value of class rule.
                 interface : ifIndex
                 ipv4acl : 2000..3999
                 ipv6acl : 2000..42767
                 greater-than : 0..65535
                 less-than : 0..65535
                 tcp : 0..65535
                 udp : 0..65535
                 mpls(exp-mask) : 1..255
                 other types: 0.
                "
            ::= { hpnicfIfQoSCQClassRuleEntry 2 }

        hpnicfIfQoSCQClassRuleQueueID OBJECT-TYPE
            SYNTAX Integer32( 1..16)
            MAX-ACCESS read-create
            STATUS current
            DESCRIPTION
                "Specify the queue for matched packets."
            ::= { hpnicfIfQoSCQClassRuleEntry 3 }

        hpnicfIfQoSCQClassRowStatus OBJECT-TYPE
            SYNTAX RowStatus
            MAX-ACCESS read-create
            STATUS current
            DESCRIPTION
                "RowStatus."
            ::= { hpnicfIfQoSCQClassRuleEntry 4 }
--
-- nodes of hpnicfIfQoSCQApplyTable
--

        hpnicfIfQoSCQApplyTable OBJECT-TYPE
            SYNTAX SEQUENCE OF HpnicfIfQoSCQApplyEntry
            MAX-ACCESS not-accessible
            STATUS current
            DESCRIPTION
                "A table of custom queue instance."
            ::= { hpnicfIfQoSCQConfigGroup 4 }

        hpnicfIfQoSCQApplyEntry OBJECT-TYPE
            SYNTAX HpnicfIfQoSCQApplyEntry
            MAX-ACCESS not-accessible
            STATUS current
            DESCRIPTION
                "Custom queue instance information."
            INDEX { ifIndex }
            ::= { hpnicfIfQoSCQApplyTable 1 }

        HpnicfIfQoSCQApplyEntry ::=
            SEQUENCE
            {
                hpnicfIfQoSCQApplyListNumber
                    Integer32,
                hpnicfIfQoSCQApplyRowStatus
                    RowStatus
            }

        hpnicfIfQoSCQApplyListNumber OBJECT-TYPE
            SYNTAX Integer32 (1..16)
            MAX-ACCESS read-create
            STATUS current
            DESCRIPTION
                "Custom queue list number."
            ::= { hpnicfIfQoSCQApplyEntry 1 }

        hpnicfIfQoSCQApplyRowStatus OBJECT-TYPE
            SYNTAX RowStatus
            MAX-ACCESS read-create
            STATUS current
            DESCRIPTION
                "RowStatus."
            ::= { hpnicfIfQoSCQApplyEntry 2 }
--
-- Nodes of hpnicfIfQoSCQRunInfoGroup
--
        hpnicfIfQoSCQRunInfoGroup OBJECT IDENTIFIER ::= { hpnicfIfQoSCQObject 2 }

        hpnicfIfQoSCQRunInfoTable OBJECT-TYPE
            SYNTAX SEQUENCE OF HpnicfIfQoSCQRunInfoEntry
            MAX-ACCESS not-accessible
            STATUS current
            DESCRIPTION
                "A table of custom queue statistic information."
            ::= { hpnicfIfQoSCQRunInfoGroup 1 }

        hpnicfIfQoSCQRunInfoEntry OBJECT-TYPE
            SYNTAX HpnicfIfQoSCQRunInfoEntry
            MAX-ACCESS not-accessible
            STATUS current
            DESCRIPTION
                "Custom queue statistic information entry."
            INDEX { ifIndex,
                    hpnicfIfQoSCQQueueID }
            ::= { hpnicfIfQoSCQRunInfoTable 1 }

        HpnicfIfQoSCQRunInfoEntry    ::=
            SEQUENCE
            {
                hpnicfIfQoSCQRunInfoSize
                    Integer32,
                hpnicfIfQoSCQRunInfoLength
                    Integer32,
                hpnicfIfQoSCQRunInfoDiscardPackets
                    Counter64
            }

        hpnicfIfQoSCQRunInfoSize OBJECT-TYPE
            SYNTAX Integer32
            MAX-ACCESS read-only
            STATUS current
            DESCRIPTION
                "The number of packets in the custom queue."
            ::= { hpnicfIfQoSCQRunInfoEntry 1 }

        hpnicfIfQoSCQRunInfoLength OBJECT-TYPE
            SYNTAX Integer32
            MAX-ACCESS read-only
            STATUS current
            DESCRIPTION
                "The maximum length of custom queue."
            ::= { hpnicfIfQoSCQRunInfoEntry 2 }

        hpnicfIfQoSCQRunInfoDiscardPackets    OBJECT-TYPE
            SYNTAX Counter64
            MAX-ACCESS read-only
            STATUS current
            DESCRIPTION
                "The packet number of custom queue discard."
            ::= { hpnicfIfQoSCQRunInfoEntry 3 }
--
-- nodes of hpnicfIfQoSWFQObject
--
        hpnicfIfQoSWFQObject OBJECT IDENTIFIER ::= { hpnicfIfQoSSoftwareQueueObjects 4 }

        hpnicfIfQoSWFQConfigGroup OBJECT IDENTIFIER ::= { hpnicfIfQoSWFQObject 1 }

        hpnicfIfQoSWFQTable OBJECT-TYPE
            SYNTAX SEQUENCE OF HpnicfIfQoSWFQEntry
            MAX-ACCESS not-accessible
            STATUS current
            DESCRIPTION
                "A table of weighted fair queue information."
            ::= { hpnicfIfQoSWFQConfigGroup 1 }

        hpnicfIfQoSWFQEntry OBJECT-TYPE
            SYNTAX HpnicfIfQoSWFQEntry
            MAX-ACCESS not-accessible
            STATUS current
            DESCRIPTION
                "Weighted fair queue information entry."
            INDEX { ifIndex }
            ::= { hpnicfIfQoSWFQTable 1 }

        HpnicfIfQoSWFQEntry ::=
            SEQUENCE
            {
                hpnicfIfQoSWFQQueueLength
                    Integer32,
                hpnicfIfQoSWFQQueueNumber
                    INTEGER,
                hpnicfIfQoSWFQRowStatus
                    RowStatus,
                hpnicfIfQoSWFQType
                    INTEGER
            }

        hpnicfIfQoSWFQQueueLength OBJECT-TYPE
            SYNTAX Integer32 (1..1024)
            MAX-ACCESS read-create
            STATUS current
            DESCRIPTION
                "The length of weighted fair queue."
            DEFVAL { 64 }
            ::= { hpnicfIfQoSWFQEntry 1 }

        hpnicfIfQoSWFQQueueNumber OBJECT-TYPE
            SYNTAX INTEGER
            {
                size16(1),
                size32(2),
                size64(3),
                size128(4),
                size256(5),
                size512(6),
                size1024(7),
                size2048(8),
                size4096(9)
            }
            MAX-ACCESS read-create
            STATUS current
            DESCRIPTION
                "The number of weighted fair queue."
            DEFVAL { 5 }
            ::= { hpnicfIfQoSWFQEntry 2 }

        hpnicfIfQoSWFQRowStatus  OBJECT-TYPE
            SYNTAX RowStatus
            MAX-ACCESS read-create
            STATUS current
            DESCRIPTION
                "RowStatus."
            ::= { hpnicfIfQoSWFQEntry 3 }

        hpnicfIfQoSWFQType OBJECT-TYPE
            SYNTAX INTEGER
            {
                ip-precedence(1),
                dscp(2)
            }
            MAX-ACCESS read-create
            STATUS current
            DESCRIPTION
                "The type of weighted fair queue."
            DEFVAL { 1 }
            ::= { hpnicfIfQoSWFQEntry 4 }
--
-- nodes of hpnicfIfQoSWFQRunInfoGroup
--
        hpnicfIfQoSWFQRunInfoGroup OBJECT IDENTIFIER ::= { hpnicfIfQoSWFQObject 2 }

        hpnicfIfQoSWFQRunInfoTable OBJECT-TYPE
            SYNTAX SEQUENCE OF HpnicfIfQoSWFQRunInfoEntry
            MAX-ACCESS not-accessible
            STATUS current
            DESCRIPTION
                "A table of weighted fair queue statistic information."
            ::= { hpnicfIfQoSWFQRunInfoGroup 1 }

        hpnicfIfQoSWFQRunInfoEntry OBJECT-TYPE
            SYNTAX HpnicfIfQoSWFQRunInfoEntry
            MAX-ACCESS not-accessible
            STATUS current
            DESCRIPTION
                "Weighted fair queue statistic information entry."
            INDEX { ifIndex }
            ::= { hpnicfIfQoSWFQRunInfoTable 1 }

        HpnicfIfQoSWFQRunInfoEntry ::=
            SEQUENCE
            {
                hpnicfIfQoSWFQSize
                    Integer32,
                hpnicfIfQoSWFQLength
                    Integer32,
                hpnicfIfQoSWFQDiscardPackets
                    Counter64,
                hpnicfIfQoSWFQHashedActiveQueues
                    Integer32,
                hpnicfIfQoSWFQHashedMaxActiveQueues
                    Integer32,
                hpnicfIfQosWFQhashedTotalQueues
                    Integer32
            }

        hpnicfIfQoSWFQSize OBJECT-TYPE
            SYNTAX Integer32
            MAX-ACCESS read-only
            STATUS current
            DESCRIPTION
                "The number of packets in all the queues"
            ::= { hpnicfIfQoSWFQRunInfoEntry 1 }

        hpnicfIfQoSWFQLength OBJECT-TYPE
            SYNTAX Integer32
            MAX-ACCESS read-only
            STATUS current
            DESCRIPTION
                "The length of weighted fair queue."
            ::= { hpnicfIfQoSWFQRunInfoEntry 2 }

        hpnicfIfQoSWFQDiscardPackets OBJECT-TYPE
            SYNTAX Counter64
            MAX-ACCESS read-only
            STATUS current
            DESCRIPTION
                "The number of discarded packets in all the queues."
            ::= { hpnicfIfQoSWFQRunInfoEntry 3 }

        hpnicfIfQoSWFQHashedActiveQueues OBJECT-TYPE
            SYNTAX Integer32
            MAX-ACCESS read-only
            STATUS current
            DESCRIPTION
                "The number of active queues."
            ::= { hpnicfIfQoSWFQRunInfoEntry 4 }

        hpnicfIfQoSWFQHashedMaxActiveQueues OBJECT-TYPE
            SYNTAX Integer32
            MAX-ACCESS read-only
            STATUS current
            DESCRIPTION
                "The number of maximum active queues."
            ::= { hpnicfIfQoSWFQRunInfoEntry 5 }

        hpnicfIfQosWFQhashedTotalQueues   OBJECT-TYPE
            SYNTAX Integer32
            MAX-ACCESS read-only
            STATUS current
            DESCRIPTION
                "The number of queues."
            ::= { hpnicfIfQoSWFQRunInfoEntry 6 }
--
-- nodes of hpnicfIfQoSBandwidthGroup
--
        hpnicfIfQoSBandwidthGroup OBJECT IDENTIFIER ::= { hpnicfIfQoSSoftwareQueueObjects 5 }

        hpnicfIfQoSBandwidthTable OBJECT-TYPE
            SYNTAX SEQUENCE OF HpnicfIfQoSBandwidthEntry
            MAX-ACCESS not-accessible
            STATUS current
            DESCRIPTION
                "A table of bandwidth of interface information."
            ::= { hpnicfIfQoSBandwidthGroup 1 }

        hpnicfIfQoSBandwidthEntry OBJECT-TYPE
            SYNTAX HpnicfIfQoSBandwidthEntry
            MAX-ACCESS not-accessible
            STATUS current
            DESCRIPTION
                "Bandwidth information entry."
            INDEX { ifIndex }
            ::= { hpnicfIfQoSBandwidthTable 1 }

        HpnicfIfQoSBandwidthEntry ::=
            SEQUENCE
            {
                hpnicfIfQoSMaxBandwidth
                    Integer32,
                hpnicfIfQoSReservedBandwidthPct
                    Integer32,
                hpnicfIfQoSBandwidthRowStatus
                    RowStatus
            }

        hpnicfIfQoSMaxBandwidth OBJECT-TYPE
            SYNTAX Integer32
            MAX-ACCESS read-create
            STATUS current
            DESCRIPTION
                "The maximum bandwidth of interface.  Unit : Kbps"
            ::= { hpnicfIfQoSBandwidthEntry 1 }

        hpnicfIfQoSReservedBandwidthPct OBJECT-TYPE
            SYNTAX Integer32 (1..100)
            MAX-ACCESS read-create
            STATUS current
            DESCRIPTION
                "Max reserved bandwidth of the interface for QoS."
            DEFVAL { 75 }
            ::= { hpnicfIfQoSBandwidthEntry 2 }

        hpnicfIfQoSBandwidthRowStatus OBJECT-TYPE
            SYNTAX RowStatus
            MAX-ACCESS read-create
            STATUS current
            DESCRIPTION
                "RowStatus."
            ::= { hpnicfIfQoSBandwidthEntry 3 }
--
-- nodes of hpnicfIfQoSQmtokenGroup
--
        hpnicfIfQoSQmtokenGroup OBJECT IDENTIFIER ::= { hpnicfIfQoSSoftwareQueueObjects 6 }

        hpnicfIfQoSQmtokenTable OBJECT-TYPE
            SYNTAX SEQUENCE OF HpnicfIfQoSQmtokenEntry
            MAX-ACCESS not-accessible
            STATUS current
            DESCRIPTION
                "A table of qmtoken information."
            ::= { hpnicfIfQoSQmtokenGroup 1 }

        hpnicfIfQoSQmtokenEntry OBJECT-TYPE
            SYNTAX HpnicfIfQoSQmtokenEntry
            MAX-ACCESS not-accessible
            STATUS current
            DESCRIPTION
                "Qmtoken information entry."
            INDEX { ifIndex }
            ::= { hpnicfIfQoSQmtokenTable 1 }

        HpnicfIfQoSQmtokenEntry ::=
            SEQUENCE
            {
                hpnicfIfQoSQmtokenNumber
                    Integer32,
                hpnicfIfQoSQmtokenRosStatus
                    RowStatus
            }

        hpnicfIfQoSQmtokenNumber OBJECT-TYPE
            SYNTAX Integer32 (1..50)
            MAX-ACCESS read-create
            STATUS current
            DESCRIPTION
                "The number of tokens."
            ::= { hpnicfIfQoSQmtokenEntry 1 }

        hpnicfIfQoSQmtokenRosStatus OBJECT-TYPE
            SYNTAX RowStatus
            MAX-ACCESS read-create
            STATUS current
            DESCRIPTION
                "RowStatus"
            ::= { hpnicfIfQoSQmtokenEntry 2 }

--
-- nodes of hpnicfIfQoSRTPQObject
--
        hpnicfIfQoSRTPQObject OBJECT IDENTIFIER ::= { hpnicfIfQoSSoftwareQueueObjects 7 }

        hpnicfIfQoSRTPQConfigGroup OBJECT IDENTIFIER ::= { hpnicfIfQoSRTPQObject 1 }

        hpnicfIfQoSRTPQConfigTable OBJECT-TYPE
            SYNTAX SEQUENCE OF HpnicfIfQoSRTPQConfigEntry
            MAX-ACCESS not-accessible
            STATUS current
            DESCRIPTION
                "A table of Real-time protocol queue information."
            ::= { hpnicfIfQoSRTPQConfigGroup 1 }

        hpnicfIfQoSRTPQConfigEntry OBJECT-TYPE
            SYNTAX HpnicfIfQoSRTPQConfigEntry
            MAX-ACCESS not-accessible
            STATUS current
            DESCRIPTION
                "The information of Real-time protocol queue entry."
            INDEX { ifIndex }
            ::= { hpnicfIfQoSRTPQConfigTable 1 }

        HpnicfIfQoSRTPQConfigEntry ::=
            SEQUENCE
            {
                hpnicfIfQoSRTPQStartPort
                    Integer32,
                hpnicfIfQoSRTPQEndPort
                    Integer32,
                hpnicfIfQoSRTPQReservedBandwidth
                    Integer32,
                hpnicfIfQoSRTPQCbs
                    Unsigned32,
                hpnicfIfQoSRTPQRowStatus
                    RowStatus
            }

        hpnicfIfQoSRTPQStartPort OBJECT-TYPE
            SYNTAX Integer32 (2000..65535)
            MAX-ACCESS read-create
            STATUS current
            DESCRIPTION
                "Minimum threshold of UDP destination port."
            ::= { hpnicfIfQoSRTPQConfigEntry 1 }

        hpnicfIfQoSRTPQEndPort OBJECT-TYPE
            SYNTAX Integer32 (2000..65535)
            MAX-ACCESS read-create
            STATUS current
            DESCRIPTION
                "Maximum threshold of UDP destination port."
            ::= { hpnicfIfQoSRTPQConfigEntry 2 }

        hpnicfIfQoSRTPQReservedBandwidth OBJECT-TYPE
            SYNTAX Integer32
            MAX-ACCESS read-create
            STATUS current
            DESCRIPTION
                "Maximum bandwidth.  unit : kbps"
            ::= { hpnicfIfQoSRTPQConfigEntry 3 }

        hpnicfIfQoSRTPQCbs OBJECT-TYPE
            SYNTAX Unsigned32
            MAX-ACCESS read-create
            STATUS current
            DESCRIPTION
                "Committed Burst Size. Unit: byte"
            ::= { hpnicfIfQoSRTPQConfigEntry 4 }

        hpnicfIfQoSRTPQRowStatus OBJECT-TYPE
            SYNTAX RowStatus
            MAX-ACCESS read-create
            STATUS current
            DESCRIPTION
                "RowStatus."
            ::= { hpnicfIfQoSRTPQConfigEntry 5 }
--
-- nodes of hpnicfIfQoSRTPQRunInfoGroup
--
        hpnicfIfQoSRTPQRunInfoGroup OBJECT IDENTIFIER ::= { hpnicfIfQoSRTPQObject 2 }

        hpnicfIfQoSRTPQRunInfoTable OBJECT-TYPE
            SYNTAX SEQUENCE OF HpnicfIfQoSRTPQRunInfoEntry
            MAX-ACCESS not-accessible
            STATUS current
            DESCRIPTION
                "A table of statistic information of Real-time protocol information."
            ::= { hpnicfIfQoSRTPQRunInfoGroup 1 }

        hpnicfIfQoSRTPQRunInfoEntry OBJECT-TYPE
            SYNTAX HpnicfIfQoSRTPQRunInfoEntry
            MAX-ACCESS not-accessible
            STATUS current
            DESCRIPTION
                "Statistic information of Real-time protocol information entry."
            INDEX { ifIndex }
            ::= { hpnicfIfQoSRTPQRunInfoTable 1 }

        HpnicfIfQoSRTPQRunInfoEntry ::=
            SEQUENCE
            {
                hpnicfIfQoSRTPQPacketNumber
                    Integer32,
                hpnicfIfQoSRTPQPacketSize
                    Integer32,
                hpnicfIfQoSRTPQOutputPackets
                    Counter64,
                hpnicfIfQoSRTPQDiscardPackets
                    Counter64
            }

        hpnicfIfQoSRTPQPacketNumber OBJECT-TYPE
            SYNTAX Integer32
            MAX-ACCESS read-only
            STATUS current
            DESCRIPTION
                "The number of packets in the Real-time protocol queue."
            ::= { hpnicfIfQoSRTPQRunInfoEntry 1 }

        hpnicfIfQoSRTPQPacketSize OBJECT-TYPE
            SYNTAX Integer32
            MAX-ACCESS read-only
            STATUS current
            DESCRIPTION
                "The size of Real-time protocol queue."
            ::= { hpnicfIfQoSRTPQRunInfoEntry 2 }

        hpnicfIfQoSRTPQOutputPackets OBJECT-TYPE
            SYNTAX Counter64
            MAX-ACCESS read-only
            STATUS current
            DESCRIPTION
                "The number of output packets."
            ::= { hpnicfIfQoSRTPQRunInfoEntry 3 }

        hpnicfIfQoSRTPQDiscardPackets OBJECT-TYPE
            SYNTAX Counter64
            MAX-ACCESS read-only
            STATUS current
            DESCRIPTION
                "The number of discard packets."
            ::= { hpnicfIfQoSRTPQRunInfoEntry 4 }

--
-- nodes of hpnicfIfQoSCarListObject
--
       hpnicfIfQoSCarListObject OBJECT IDENTIFIER ::= { hpnicfIfQoSSoftwareQueueObjects 8 }

       hpnicfIfQoCarListGroup OBJECT IDENTIFIER ::= { hpnicfIfQoSCarListObject 1 }

       hpnicfIfQoSCarlTable OBJECT-TYPE
            SYNTAX SEQUENCE OF HpnicfIfQoSCarlEntry
            MAX-ACCESS not-accessible
            STATUS current
            DESCRIPTION
                   "Committed Access Rate List(CARL) table."
            ::= { hpnicfIfQoCarListGroup 1 }

        hpnicfIfQoSCarlEntry OBJECT-TYPE
            SYNTAX HpnicfIfQoSCarlEntry
            MAX-ACCESS not-accessible
            STATUS current
            DESCRIPTION
                    "CARL configuration information."
            INDEX { hpnicfIfQoSCarlListNum }
            ::= { hpnicfIfQoSCarlTable 1 }

        HpnicfIfQoSCarlEntry ::=
            SEQUENCE {
                         hpnicfIfQoSCarlListNum
                             Integer32,
                         hpnicfIfQoSCarlParaType
                             INTEGER,
                         hpnicfIfQoSCarlParaValue
                             OCTET STRING,
                         hpnicfIfQoSCarlRowStatus
                             RowStatus
                     }

        hpnicfIfQoSCarlListNum OBJECT-TYPE
            SYNTAX Integer32
            MAX-ACCESS not-accessible
            STATUS current
            DESCRIPTION
                    "The index of the table, which is the CARL number."
            ::= { hpnicfIfQoSCarlEntry 1 }

        hpnicfIfQoSCarlParaType OBJECT-TYPE
            SYNTAX INTEGER
                    {
                        macAddress(1),
                        precMask(2),
                        dscpMask(3)
                    }
            MAX-ACCESS read-create
            STATUS current
            DESCRIPTION
                    "Parameter type of the CARL number."
            ::= { hpnicfIfQoSCarlEntry 2 }

        hpnicfIfQoSCarlParaValue OBJECT-TYPE
            SYNTAX OCTET STRING
            MAX-ACCESS read-create
            STATUS current
            DESCRIPTION
                    "Parameter value of the CARL table."
            ::= { hpnicfIfQoSCarlEntry 3 }

        hpnicfIfQoSCarlRowStatus OBJECT-TYPE
            SYNTAX RowStatus
            MAX-ACCESS read-create
            STATUS current
            DESCRIPTION
               "RowStatus."
            ::= { hpnicfIfQoSCarlEntry 4 }

--
-- nodes of hpnicfIfQoSLineRateObject
--
        hpnicfIfQoSLineRateObjects OBJECT IDENTIFIER ::= { hpnicfIfQos2 3 }

        hpnicfIfQoSLRConfigTable OBJECT-TYPE
            SYNTAX SEQUENCE OF HpnicfIfQoSLRConfigEntry
            MAX-ACCESS not-accessible
            STATUS current
            DESCRIPTION
                "A table of line rate configuration information."
            ::= { hpnicfIfQoSLineRateObjects 1 }

        hpnicfIfQoSLRConfigEntry OBJECT-TYPE
            SYNTAX HpnicfIfQoSLRConfigEntry
            MAX-ACCESS not-accessible
            STATUS current
            DESCRIPTION
                "Line rate configuration information entry."
            INDEX { ifIndex, hpnicfIfQoSLRDirection }
            ::= { hpnicfIfQoSLRConfigTable 1 }

        HpnicfIfQoSLRConfigEntry ::=
            SEQUENCE
            {
                hpnicfIfQoSLRDirection
                    Direction,
                hpnicfIfQoSLRCir
                    Unsigned32,
                hpnicfIfQoSLRCbs
                    Unsigned32,
                hpnicfIfQoSLREbs
                    Unsigned32,
                hpnicfIfQoSRowStatus
                    RowStatus,
                hpnicfIfQoSLRPir
                    Unsigned32,
                hpnicfIfQoSLRUnit
                    INTEGER
            }

        hpnicfIfQoSLRDirection OBJECT-TYPE
            SYNTAX Direction
            MAX-ACCESS not-accessible
            STATUS current
            DESCRIPTION
                "Line rate on the inbound or outbound of data stream."
            ::= { hpnicfIfQoSLRConfigEntry 1 }

        hpnicfIfQoSLRCir OBJECT-TYPE
            SYNTAX Unsigned32
            MAX-ACCESS read-create
            STATUS current
            DESCRIPTION
                "Committed Information Rate."
            ::= { hpnicfIfQoSLRConfigEntry 2 }

        hpnicfIfQoSLRCbs  OBJECT-TYPE
            SYNTAX Unsigned32
            MAX-ACCESS read-create
            STATUS current
            DESCRIPTION
                "Committed Burst Size."
            ::= { hpnicfIfQoSLRConfigEntry 3 }

        hpnicfIfQoSLREbs  OBJECT-TYPE
            SYNTAX Unsigned32
            MAX-ACCESS read-create
            STATUS current
            DESCRIPTION
                "Excess Burst Size."
            ::= { hpnicfIfQoSLRConfigEntry 4 }

        hpnicfIfQoSRowStatus  OBJECT-TYPE
            SYNTAX RowStatus
            MAX-ACCESS read-create
            STATUS current
            DESCRIPTION
                "RowStatus."
            ::= { hpnicfIfQoSLRConfigEntry 5 }

        hpnicfIfQoSLRPir OBJECT-TYPE
            SYNTAX Unsigned32
            MAX-ACCESS read-create
            STATUS current
            DESCRIPTION
                "Peak Information Rate."
            ::= { hpnicfIfQoSLRConfigEntry 6 }

        hpnicfIfQoSLRUnit OBJECT-TYPE
            SYNTAX INTEGER
            {
                unitAbsolute(1),
                unitPercent(2)
            }
            MAX-ACCESS read-create
            STATUS current
            DESCRIPTION
                "LR Unit:
                 Absolute, Unit Kbps (1)
                 Percent, Unit % (2)
                "
            DEFVAL { unitAbsolute }
            ::= { hpnicfIfQoSLRConfigEntry 7 }

--
-- nodes of hpnicfIfQoSLRRunInfoTable
--
        hpnicfIfQoSLRRunInfoTable OBJECT-TYPE
            SYNTAX SEQUENCE OF HpnicfIfQoSLRRunInfoEntry
            MAX-ACCESS not-accessible
            STATUS current
            DESCRIPTION
                "A table of line rate run info information."
            ::= { hpnicfIfQoSLineRateObjects 2 }

        hpnicfIfQoSLRRunInfoEntry OBJECT-TYPE
            SYNTAX HpnicfIfQoSLRRunInfoEntry
            MAX-ACCESS not-accessible
            STATUS current
            DESCRIPTION
                "Line rate run info information entry."
            INDEX { ifIndex, hpnicfIfQoSLRDirection }
            ::= { hpnicfIfQoSLRRunInfoTable 1 }

        HpnicfIfQoSLRRunInfoEntry ::=
            SEQUENCE
            {
                hpnicfIfQoSLRRunInfoPassedPackets
                    Counter64,
                hpnicfIfQoSLRRunInfoPassedBytes
                    Counter64,
                hpnicfIfQoSLRRunInfoDelayedPackets
                    Counter64,
                hpnicfIfQoSLRRunInfoDelayedBytes
                    Counter64,
                hpnicfIfQoSLRRunInfoActiveShaping
                    INTEGER
            }

        hpnicfIfQoSLRRunInfoPassedPackets OBJECT-TYPE
            SYNTAX Counter64
            MAX-ACCESS read-only
            STATUS current
            DESCRIPTION
                "The number of passed packets."
            ::= { hpnicfIfQoSLRRunInfoEntry 1 }

        hpnicfIfQoSLRRunInfoPassedBytes OBJECT-TYPE
            SYNTAX Counter64
            MAX-ACCESS read-only
            STATUS current
            DESCRIPTION
                "The number of passed bytes."
            ::= { hpnicfIfQoSLRRunInfoEntry 2 }

        hpnicfIfQoSLRRunInfoDelayedPackets OBJECT-TYPE
            SYNTAX Counter64
            MAX-ACCESS read-only
            STATUS current
            DESCRIPTION
                "The number of delayed packets."
            ::= { hpnicfIfQoSLRRunInfoEntry 3 }

        hpnicfIfQoSLRRunInfoDelayedBytes OBJECT-TYPE
            SYNTAX Counter64
            MAX-ACCESS read-only
            STATUS current
            DESCRIPTION
                "The number of delayed bytes."
            ::= { hpnicfIfQoSLRRunInfoEntry 4 }

        hpnicfIfQoSLRRunInfoActiveShaping OBJECT-TYPE
            SYNTAX INTEGER
            {
                active(1),
                inactive(2)
            }
            MAX-ACCESS read-only
            STATUS current
            DESCRIPTION
                "The flag of shaping."
            ::= { hpnicfIfQoSLRRunInfoEntry 5 }

--
-- nodes of car group
--
        hpnicfIfQoSCARObjects OBJECT IDENTIFIER ::= { hpnicfIfQos2 4 }
--
-- nodes of hpnicfIfQoSAggregativeCarGroup
--
        hpnicfIfQoSAggregativeCarGroup OBJECT IDENTIFIER ::= { hpnicfIfQoSCARObjects 1 }
--
-- nodes of hpnicfIfQoSAggregativeCarConfigTable
--
        hpnicfIfQoSAggregativeCarNextIndex OBJECT-TYPE
            SYNTAX Integer32
            MAX-ACCESS read-only
            STATUS current
            DESCRIPTION
                "This object contains an appropriate value to be used for hpnicfIfQoSAggregativeCarIndex
                 when creating rows in the hpnicfIfQoSAggregativeCarConfigTable.
                 Begin with 1.
                "
            ::= { hpnicfIfQoSAggregativeCarGroup 1 }

        hpnicfIfQoSAggregativeCarConfigTable OBJECT-TYPE
            SYNTAX SEQUENCE OF HpnicfIfQoSAggregativeCarConfigEntry
            MAX-ACCESS not-accessible
            STATUS current
            DESCRIPTION
                "A table of aggregative car information."
            ::= { hpnicfIfQoSAggregativeCarGroup 2 }

        hpnicfIfQoSAggregativeCarConfigEntry OBJECT-TYPE
            SYNTAX HpnicfIfQoSAggregativeCarConfigEntry
            MAX-ACCESS not-accessible
            STATUS current
            DESCRIPTION
                "Aggregative car information."
            INDEX { hpnicfIfQoSAggregativeCarIndex }
            ::= { hpnicfIfQoSAggregativeCarConfigTable 1 }

        HpnicfIfQoSAggregativeCarConfigEntry     ::=
            SEQUENCE
            {
                hpnicfIfQoSAggregativeCarIndex
                    Integer32,
                hpnicfIfQoSAggregativeCarName
                    OCTET STRING,
                hpnicfIfQoSAggregativeCarCir
                    Unsigned32,
                hpnicfIfQoSAggregativeCarCbs
                    Unsigned32,
                hpnicfIfQoSAggregativeCarEbs
                    Unsigned32,
                hpnicfIfQoSAggregativeCarPir
                    Unsigned32,
                hpnicfIfQoSAggregativeCarGreenActionType
                    HpnicfIfCarAction,
                hpnicfIfQoSAggregativeCarGreenActionValue
                    Integer32,
                hpnicfIfQoSAggregativeCarYellowActionType
                    HpnicfIfCarAction,
                hpnicfIfQoSAggregativeCarYellowActionValue
                    Integer32,
                hpnicfIfQoSAggregativeCarRedActionType
                    HpnicfIfCarAction,
                hpnicfIfQoSAggregativeCarRedActionValue
                    Integer32,
                hpnicfIfQoSAggregativeCarType
                    INTEGER,
                hpnicfIfQoSAggregativeCarRowStatus
                    RowStatus
            }

        hpnicfIfQoSAggregativeCarIndex OBJECT-TYPE
            SYNTAX Integer32 (1..65534)
            MAX-ACCESS not-accessible
            STATUS current
            DESCRIPTION
                "The index of aggregative car."
            ::= { hpnicfIfQoSAggregativeCarConfigEntry 1 }

        hpnicfIfQoSAggregativeCarName OBJECT-TYPE
            SYNTAX OCTET STRING (SIZE(1..31))
            MAX-ACCESS read-create
            STATUS current
            DESCRIPTION
                "The name of aggregative car."
            ::= { hpnicfIfQoSAggregativeCarConfigEntry 2 }

        hpnicfIfQoSAggregativeCarCir OBJECT-TYPE
            SYNTAX Unsigned32
            MAX-ACCESS read-create
            STATUS current
            DESCRIPTION
                "Committed-information-rate.  Unit : kbps"
            ::= { hpnicfIfQoSAggregativeCarConfigEntry 3 }

        hpnicfIfQoSAggregativeCarCbs OBJECT-TYPE
            SYNTAX Unsigned32
            MAX-ACCESS read-create
            STATUS current
            DESCRIPTION
                "Committed-burst-size.  Unit : byte"
            ::= { hpnicfIfQoSAggregativeCarConfigEntry 4 }

        hpnicfIfQoSAggregativeCarEbs OBJECT-TYPE
            SYNTAX Unsigned32
            MAX-ACCESS read-create
            STATUS current
            DESCRIPTION
                "Excess-burst-size.  Unit : byte"
            ::= { hpnicfIfQoSAggregativeCarConfigEntry 5 }

        hpnicfIfQoSAggregativeCarPir OBJECT-TYPE
            SYNTAX Unsigned32
            MAX-ACCESS read-create
            STATUS current
            DESCRIPTION
                "Peak-information-rate.  Unit : kbps"
            DEFVAL { 4294967295 }
            ::= { hpnicfIfQoSAggregativeCarConfigEntry 6 }

        hpnicfIfQoSAggregativeCarGreenActionType OBJECT-TYPE
            SYNTAX HpnicfIfCarAction
            MAX-ACCESS read-create
            STATUS current
            DESCRIPTION
                "Supported green action:
                 invalid(0),
                 pass(1),
                 discard(3),
                 remark(4),
                 remark-ip-pass(6),
                 remark-mplsexp-pass(8),
                 remark-dscp-pass(10),
                 remark-dot1p-pass(12),
                 remark-atm-clp-pass(14),
                 remark-fr-de-pass(16),
                 remarkLocalPrePass(18),
                 remarkDropPrePass(20).
                 Hardware QoS : pass, discard, remark.
                 Software QoS : pass, discard, remark-ip-pass(6),
                 remark-mplsexp-pass(8), remark-dscp-pass(10).
                 'invalid' is returned when getting value from software QoS.
                 "
            DEFVAL { pass }
            ::= { hpnicfIfQoSAggregativeCarConfigEntry 7 }

        hpnicfIfQoSAggregativeCarGreenActionValue OBJECT-TYPE
            SYNTAX Integer32 (0..63|255)
            MAX-ACCESS read-create
            STATUS current
            DESCRIPTION
                "The value is to remark When green action is remarking.
                 For remark-dscp-pass, the range is 0 to 63;
                 For remark-ip-pass, remark-mplsexp-pass, remark-dot1p-pass and
                 remarkLocalPrePass, the range is 0 to 7;
                 For remark-fr-de-pass and remark-atm-clp-pass, the range is 0 to 1;
                 For remarkDropPrePass, the range is 0 to 2.
                 Only software QoS support this node.
                 255 is returned only when getting value from hardware QoS or
                 when action being pass, discard of software QoS.
                 255 can't be set.
                "
            ::= { hpnicfIfQoSAggregativeCarConfigEntry 8 }

        hpnicfIfQoSAggregativeCarYellowActionType OBJECT-TYPE
            SYNTAX HpnicfIfCarAction
            MAX-ACCESS read-create
            STATUS current
            DESCRIPTION
                "Supported yellow action:
                 invalid(0),
                 pass(1),
                 discard(3),
                 remark(4),
                 remark-ip-pass(6),
                 remark-mplsexp-pass(8),
                 remark-dscp-pass(10),
                 remark-dot1p-pass(12),
                 remark-atm-clp-pass(14),
                 remark-fr-de-pass(16),
                 remarkLocalPrePass(18),
                 remarkDropPrePass(20).
                 Hardware QoS : pass, discard, remark.
                 Software QoS : pass, discard, remark-ip-pass(6),
                 remark-mplsexp-pass(8), remark-dscp-pass(10).
                 'invalid' is returned when getting value from software QoS.
                "
            ::= { hpnicfIfQoSAggregativeCarConfigEntry 9 }

        hpnicfIfQoSAggregativeCarYellowActionValue OBJECT-TYPE
            SYNTAX Integer32 (0..63|255)
            MAX-ACCESS read-create
            STATUS current
            DESCRIPTION
                "The value is to remark When yellow action is remarking.
                 For remark-dscp-pass, the range is 0 to 63;
                 For remark-ip-pass, remark-mplsexp-pass, remark-dot1p-pass and
                 remarkLocalPrePass, the range is 0 to 7;
                 For remark-fr-de-pass and remark-atm-clp-pass, the range is 0 to 1;
                 For remarkDropPrePass, the range is 0 to 2.
                 Only software QoS support this node.
                 255 is returned only when getting value from hardware QoS or
                 when action being pass, discard of software QoS.
                 255 can't be set.
                "
            ::= { hpnicfIfQoSAggregativeCarConfigEntry 10 }

        hpnicfIfQoSAggregativeCarRedActionType OBJECT-TYPE
            SYNTAX HpnicfIfCarAction
            MAX-ACCESS read-create
            STATUS current
            DESCRIPTION
                "Supported red action:
                 invalid(0),
                 pass(1),
                 discard(3),
                 remark(4),
                 remark-ip-pass(6),
                 remark-mplsexp-pass(8),
                 remark-dscp-pass(10),
                 remark-dot1p-pass(12),
                 remark-atm-clp-pass(14),
                 remark-fr-de-pass(16),
                 remarkLocalPrePass(18),
                 remarkDropPrePass(20).
                 Hardware QoS : pass, discard, remark.
                 Software QoS : pass, discard, remark-ip-pass(6),
                 remark-mplsexp-pass(8), remark-dscp-pass(10).
                 'invalid' is returned when getting value from software QoS.
                "
            ::= { hpnicfIfQoSAggregativeCarConfigEntry 11 }

        hpnicfIfQoSAggregativeCarRedActionValue OBJECT-TYPE
            SYNTAX Integer32 (0..63|255)
            MAX-ACCESS read-create
            STATUS current
            DESCRIPTION
                "The value is to remark When red action is remarking.
                 For remark-dscp-pass, the range is 0 to 63;
                 For remark-ip-pass, remark-mplsexp-pass, remark-dot1p-pass and
                 remarkLocalPrePass, the range is 0 to 7;
                 For remark-fr-de-pass and remark-atm-clp-pass, the range is 0 to 1;
                 For remarkDropPrePass, the range is 0 to 2.
                 Only software QoS support this node.
                 255 is returned only when getting value from hardware QoS or
                 when action being pass, discard of software QoS.
                 255 can't be set.
                "
            ::= { hpnicfIfQoSAggregativeCarConfigEntry 12 }

        hpnicfIfQoSAggregativeCarType OBJECT-TYPE
            SYNTAX INTEGER
            {
                aggregative(1),
                notAggregative(2),
                hierarchy(3)
            }
            MAX-ACCESS read-create
            STATUS current
            DESCRIPTION
                "The type of aggregative CAR.
                 The enumeration 'aggregative' indicates that the ports
                 with a same aggregative CAR use one token bulk.

                 The enumeration 'notAggregative' indicates that each port
                 uses one token bulk.

                 The enumeration 'hierarchy' indicates that each object uses one
                 token bulk after processed first by some other token bulk.
                "
            ::= { hpnicfIfQoSAggregativeCarConfigEntry 13 }

        hpnicfIfQoSAggregativeCarRowStatus OBJECT-TYPE
            SYNTAX RowStatus
            MAX-ACCESS read-create
            STATUS current
            DESCRIPTION
                "RowStatus."
            ::= { hpnicfIfQoSAggregativeCarConfigEntry 14 }
--
-- nodes of hpnicfIfQoSAggregativeCarApplyGroup
--
        hpnicfIfQoSAggregativeCarApplyTable OBJECT-TYPE
            SYNTAX SEQUENCE OF HpnicfIfQoSAggregativeCarApplyEntry
            MAX-ACCESS not-accessible
            STATUS current
            DESCRIPTION
                "A table of aggregative car instance."
            ::= { hpnicfIfQoSAggregativeCarGroup 3 }

        hpnicfIfQoSAggregativeCarApplyEntry OBJECT-TYPE
            SYNTAX HpnicfIfQoSAggregativeCarApplyEntry
            MAX-ACCESS not-accessible
            STATUS current
            DESCRIPTION
                "Aggregative car instance information."
            INDEX { ifIndex,
                    hpnicfIfQoSAggregativeCarApplyDirection,
                    hpnicfIfQoSAggregativeCarApplyRuleType,
                    hpnicfIfQoSAggregativeCarApplyRuleValue
                  }
            ::= { hpnicfIfQoSAggregativeCarApplyTable 1 }

        HpnicfIfQoSAggregativeCarApplyEntry ::=
            SEQUENCE
            {
                hpnicfIfQoSAggregativeCarApplyDirection
                    Direction,
                hpnicfIfQoSAggregativeCarApplyRuleType
                    INTEGER,
                hpnicfIfQoSAggregativeCarApplyRuleValue
                    Integer32,
                hpnicfIfQoSAggregativeCarApplyCarIndex
                    Integer32,
                hpnicfIfQoSAggregativeCarApplyRowStatus
                    RowStatus
            }

        hpnicfIfQoSAggregativeCarApplyDirection OBJECT-TYPE
            SYNTAX Direction
            MAX-ACCESS not-accessible
            STATUS current
            DESCRIPTION
                "Direction."
            ::= { hpnicfIfQoSAggregativeCarApplyEntry 1 }

        hpnicfIfQoSAggregativeCarApplyRuleType OBJECT-TYPE
            SYNTAX INTEGER
            {
                ipv4acl(1),
                ipv6acl(2),
                carl(3),
                any(4)
            }
            MAX-ACCESS not-accessible
            STATUS current
            DESCRIPTION
                "The type of class rule."
            ::= { hpnicfIfQoSAggregativeCarApplyEntry 2 }

        hpnicfIfQoSAggregativeCarApplyRuleValue OBJECT-TYPE
            SYNTAX Integer32 (0..2147483647)
            MAX-ACCESS not-accessible
            STATUS current
            DESCRIPTION
                "The number of class rule.
                 ipv4acl : 2000..5999
                 ipv6acl : 2000..42767
                 carl : 1..199
                 other types: 0.
                "
            ::= { hpnicfIfQoSAggregativeCarApplyEntry 3 }

        hpnicfIfQoSAggregativeCarApplyCarIndex OBJECT-TYPE
            SYNTAX Integer32 (1..65534)
            MAX-ACCESS read-create
            STATUS current
            DESCRIPTION
                "The index of aggregative car."
            ::= { hpnicfIfQoSAggregativeCarApplyEntry 4 }

        hpnicfIfQoSAggregativeCarApplyRowStatus OBJECT-TYPE
            SYNTAX RowStatus
            MAX-ACCESS read-create
            STATUS current
            DESCRIPTION
                "RowStatus."
            ::= { hpnicfIfQoSAggregativeCarApplyEntry 5 }
--
-- nodes of hpnicfIfQoSAggregativeCarRunInfoTable
--
        hpnicfIfQoSAggregativeCarRunInfoTable OBJECT-TYPE
            SYNTAX SEQUENCE OF HpnicfIfQoSAggregativeCarRunInfoEntry
            MAX-ACCESS not-accessible
            STATUS current
            DESCRIPTION
                "A table of aggregative car statistic information."
            ::= { hpnicfIfQoSAggregativeCarGroup 4 }

        hpnicfIfQoSAggregativeCarRunInfoEntry OBJECT-TYPE
            SYNTAX HpnicfIfQoSAggregativeCarRunInfoEntry
            MAX-ACCESS not-accessible
            STATUS current
            DESCRIPTION
                "Aggregative car statistic information."
            INDEX { hpnicfIfQoSAggregativeCarIndex }
            ::= { hpnicfIfQoSAggregativeCarRunInfoTable 1 }

        HpnicfIfQoSAggregativeCarRunInfoEntry ::=
            SEQUENCE
            {
                hpnicfIfQoSAggregativeCarGreenPackets
                    Counter64,
                hpnicfIfQoSAggregativeCarGreenBytes
                    Counter64,
                hpnicfIfQoSAggregativeCarYellowPackets
                    Counter64,
                hpnicfIfQoSAggregativeCarYellowBytes
                    Counter64,
                hpnicfIfQoSAggregativeCarRedPackets
                    Counter64,
                hpnicfIfQoSAggregativeCarRedBytes
                    Counter64
            }

        hpnicfIfQoSAggregativeCarGreenPackets OBJECT-TYPE
            SYNTAX Counter64
            MAX-ACCESS read-only
            STATUS current
            DESCRIPTION
                "Number of packets conforming CIR."
            ::= { hpnicfIfQoSAggregativeCarRunInfoEntry 1 }

        hpnicfIfQoSAggregativeCarGreenBytes OBJECT-TYPE
            SYNTAX Counter64
            MAX-ACCESS read-only
            STATUS current
            DESCRIPTION
                "Number of bytes conforming CIR"
            ::= { hpnicfIfQoSAggregativeCarRunInfoEntry 2 }

        hpnicfIfQoSAggregativeCarYellowPackets OBJECT-TYPE
            SYNTAX Counter64
            MAX-ACCESS read-only
            STATUS current
            DESCRIPTION
                "Number of yellow packets."
            ::= { hpnicfIfQoSAggregativeCarRunInfoEntry 3 }

        hpnicfIfQoSAggregativeCarYellowBytes  OBJECT-TYPE
            SYNTAX Counter64
            MAX-ACCESS read-only
            STATUS current
            DESCRIPTION
                "Number of yellow bytes."
            ::= { hpnicfIfQoSAggregativeCarRunInfoEntry 4 }

        hpnicfIfQoSAggregativeCarRedPackets OBJECT-TYPE
            SYNTAX Counter64
            MAX-ACCESS read-only
            STATUS current
            DESCRIPTION
                "Number of packets exceeding CIR."
            ::= { hpnicfIfQoSAggregativeCarRunInfoEntry 5 }

        hpnicfIfQoSAggregativeCarRedBytes OBJECT-TYPE
            SYNTAX Counter64
            MAX-ACCESS read-only
            STATUS current
            DESCRIPTION
                "Number of bytes exceeding CIR."
            ::= { hpnicfIfQoSAggregativeCarRunInfoEntry 6 }

--
-- nodes of hpnicfIfQoSTricolorCARGroup
--
        hpnicfIfQoSTricolorCarGroup OBJECT IDENTIFIER ::= { hpnicfIfQoSCARObjects 2 }
--
-- nodes of

        hpnicfIfQoSTricolorCarConfigTable OBJECT-TYPE
            SYNTAX SEQUENCE OF HpnicfIfQoSTricolorCarConfigEntry
            MAX-ACCESS not-accessible
            STATUS current
            DESCRIPTION
                "A table of tricolor car configuration information."
            ::= { hpnicfIfQoSTricolorCarGroup 1 }

        hpnicfIfQoSTricolorCarConfigEntry OBJECT-TYPE
            SYNTAX HpnicfIfQoSTricolorCarConfigEntry
            MAX-ACCESS not-accessible
            STATUS current
            DESCRIPTION
                "Tricolor car configuration information entry."
            INDEX { ifIndex,
                    hpnicfIfQoSTricolorCarDirection,
                    hpnicfIfQoSTricolorCarType,
                    hpnicfIfQoSTricolorCarValue
                  }
            ::= { hpnicfIfQoSTricolorCarConfigTable 1 }

        HpnicfIfQoSTricolorCarConfigEntry ::=
            SEQUENCE
            {
                hpnicfIfQoSTricolorCarDirection
                    Direction,
                hpnicfIfQoSTricolorCarType
                    INTEGER,
                hpnicfIfQoSTricolorCarValue
                    Integer32,
                hpnicfIfQoSTricolorCarCir
                    Unsigned32,
                hpnicfIfQoSTricolorCarCbs
                    Unsigned32,
                hpnicfIfQoSTricolorCarEbs
                    Unsigned32,
                hpnicfIfQoSTricolorCarPir
                    Unsigned32,
                hpnicfIfQoSTricolorCarGreenActionType
                    HpnicfIfCarAction,
                hpnicfIfQoSTricolorCarGreenActionValue
                    Integer32,
                hpnicfIfQoSTricolorCarYellowActionType
                    HpnicfIfCarAction,
                hpnicfIfQoSTricolorCarYellowActionValue
                    Integer32,
                hpnicfIfQoSTricolorCarRedActionType
                    HpnicfIfCarAction,
                hpnicfIfQoSTricolorCarRedActionValue
                    Integer32,
                hpnicfIfQoSTricolorCarRowStatus
                    RowStatus,
                hpnicfIfQoSTricolorCarUnitType
                    INTEGER
            }

        hpnicfIfQoSTricolorCarDirection OBJECT-TYPE
            SYNTAX Direction
            MAX-ACCESS not-accessible
            STATUS current
            DESCRIPTION
                "Direction."
            ::= { hpnicfIfQoSTricolorCarConfigEntry 1 }

        hpnicfIfQoSTricolorCarType OBJECT-TYPE
            SYNTAX INTEGER
            {
                ipv4acl(1),
                ipv6acl(2),
                carl(3),
                any(4)
            }
            MAX-ACCESS not-accessible
            STATUS current
            DESCRIPTION
                "The index of the table, which is the matching type for the
                 packets on interface: ipv4acl, ipv6acl, carl, any."
            ::= { hpnicfIfQoSTricolorCarConfigEntry 2 }

        hpnicfIfQoSTricolorCarValue OBJECT-TYPE
            SYNTAX Integer32 (0..2147483647)
            MAX-ACCESS not-accessible
            STATUS current
            DESCRIPTION
                "The index of the table.
                 ipv4acl: the number is ipv4 acl number;
                 ipv6acl: the number is ipv6 acl number;
                 carl: the number is CARL number;
                 any: the number is 0;
                "
            ::= { hpnicfIfQoSTricolorCarConfigEntry 3 }

        hpnicfIfQoSTricolorCarCir OBJECT-TYPE
            SYNTAX Unsigned32
            MAX-ACCESS read-create
            STATUS current
            DESCRIPTION
                "Committed Information Rate.  The unit of this parameter depends
                on the hpnicfIfQoSTricolorCarUnitType node.
                +-----------+----------+------------+
                | Unit type | absolute | percent    |
                +-----------+----------+------------+
                | CIR unit  | kbps     | percentage |
                +-----------+----------+------------+
                "
            ::= { hpnicfIfQoSTricolorCarConfigEntry 4 }

        hpnicfIfQoSTricolorCarCbs OBJECT-TYPE
            SYNTAX Unsigned32
            MAX-ACCESS read-create
            STATUS current
            DESCRIPTION
                "Committed Burst Size.  The unit of this parameter depends
                on the hpnicfIfQoSTricolorCarUnitType node.
                +-----------+----------+--------------+
                | Unit type | absolute | percent      |
                +-----------+----------+--------------+
                | CBS unit  | bytes    | milliseconds |
                +-----------+----------+--------------+
                "
            ::= { hpnicfIfQoSTricolorCarConfigEntry 5 }

        hpnicfIfQoSTricolorCarEbs OBJECT-TYPE
            SYNTAX Unsigned32
            MAX-ACCESS read-create
            STATUS current
            DESCRIPTION
                "Excess Burst Size.  The unit of this parameter depends
                on the hpnicfIfQoSTricolorCarUnitType node.
                +-----------+----------+--------------+
                | Unit type | absolute | percent      |
                +-----------+----------+--------------+
                | EBS unit  | bytes    | milliseconds |
                +-----------+----------+--------------+
                "
            ::= { hpnicfIfQoSTricolorCarConfigEntry 6 }

        hpnicfIfQoSTricolorCarPir OBJECT-TYPE
            SYNTAX Unsigned32
            MAX-ACCESS read-create
            STATUS current
            DESCRIPTION
                "Peak Information Rate.  The unit of this parameter depends
                on the hpnicfIfQoSTricolorCarUnitType node.
                +-----------+----------+------------+
                | Unit type | absolute | percent    |
                +-----------+----------+------------+
                | PIR unit  | kbps     | percentage |
                +-----------+----------+------------+
                "
            DEFVAL { 4294967295 }
            ::= { hpnicfIfQoSTricolorCarConfigEntry 7 }

        hpnicfIfQoSTricolorCarGreenActionType OBJECT-TYPE
            SYNTAX HpnicfIfCarAction
            MAX-ACCESS read-create
            STATUS current
            DESCRIPTION
                "Green Action."
            DEFVAL { pass }
            ::= { hpnicfIfQoSTricolorCarConfigEntry 8 }

        hpnicfIfQoSTricolorCarGreenActionValue OBJECT-TYPE
            SYNTAX Integer32 (0..63|255)
            MAX-ACCESS read-create
            STATUS current
            DESCRIPTION
                "The value is to remark when green action is remarking.
                 For remark-dscp-continue and remark-dscp-pass, the range is 0 to 63;
                 For remark-ip-continue and remark-ip-pass and
                 remark-mplsexp-continue and remark-mplsexp-pass and
                 remark-dot1p-continue and remark-dot1p-pass, the range is 0 to 7;
                 For remark-fr-de-continue and remark-fr-de-pass and
                 remark-atm-clp-continue and remark-atm-clp-pass, the range is 0 and 1.
                 255 is returned only when getting value from hardware QoS
                 or when action being pass, continue, discard of software QoS.
                 255 can't be set.
                "
            ::= { hpnicfIfQoSTricolorCarConfigEntry 9 }

        hpnicfIfQoSTricolorCarYellowActionType OBJECT-TYPE
            SYNTAX HpnicfIfCarAction
            MAX-ACCESS read-create
            STATUS current
            DESCRIPTION
                "Yellow Action."
            DEFVAL { pass }
            ::= { hpnicfIfQoSTricolorCarConfigEntry 10 }

        hpnicfIfQoSTricolorCarYellowActionValue OBJECT-TYPE
            SYNTAX Integer32 (0..63|255)
            MAX-ACCESS read-create
            STATUS current
            DESCRIPTION
                "The value is to remark when yellow action is remarking.
                 For remark-dscp-continue and remark-dscp-pass, the range is 0 to 63;
                 For remark-ip-continue and remark-ip-pass and
                 remark-mplsexp-continue and remark-mplsexp-pass and
                 remark-dot1p-continue and remark-dot1p-pass, the range is 0 to 7;
                 For remark-fr-de-continue and remark-fr-de-pass and
                 remark-atm-clp-continue and remark-atm-clp-pass, the range is 0 and 1.
                 255 is returned only when getting value from hardware QoS
                 or when action being pass, continue, discard of software QoS.
                 255 can't be set.
                "
            ::= { hpnicfIfQoSTricolorCarConfigEntry 11 }

        hpnicfIfQoSTricolorCarRedActionType OBJECT-TYPE
            SYNTAX HpnicfIfCarAction
            MAX-ACCESS read-create
            STATUS current
            DESCRIPTION
                "Red Action"
            DEFVAL { discard }
            ::= { hpnicfIfQoSTricolorCarConfigEntry 12 }

        hpnicfIfQoSTricolorCarRedActionValue OBJECT-TYPE
            SYNTAX Integer32 (0..63|255)
            MAX-ACCESS read-create
            STATUS current
            DESCRIPTION
                "The value is to remark when red action is remarking.
                 For remark-dscp-continue and remark-dscp-pass, the range is 0 to 63;
                 For remark-ip-continue and remark-ip-pass and
                 remark-mplsexp-continue and remark-mplsexp-pass and
                 remark-dot1p-continue and remark-dot1p-pass, the range is 0 to 7;
                 For remark-fr-de-continue and remark-fr-de-pass and
                 remark-atm-clp-continue and remark-atm-clp-pass, the range is 0 and 1.
                 255 is returned only when getting value from hardware QoS
                 or when action being pass, continue, discard of software QoS.
                 255 can't be set.
                "
            ::= { hpnicfIfQoSTricolorCarConfigEntry 13 }

        hpnicfIfQoSTricolorCarRowStatus OBJECT-TYPE
            SYNTAX RowStatus
            MAX-ACCESS read-create
            STATUS current
            DESCRIPTION
                "RowStatus."
            ::= { hpnicfIfQoSTricolorCarConfigEntry 14 }

        hpnicfIfQoSTricolorCarUnitType OBJECT-TYPE
            SYNTAX INTEGER
            {
                unitAbsolute(1),
                unitPercent(2)
            }
            MAX-ACCESS read-create
            STATUS current
            DESCRIPTION
                "Unit of token parameters.  If it is unitAbsolute, the token
                parameters are in kbps and bytes, and if it is unitPercent,
                the token parameters are in percentage and milliseconds."
            DEFVAL { unitAbsolute }
            ::= { hpnicfIfQoSTricolorCarConfigEntry 15 }


--
-- nodes of hpnicfIfQoSTricolorCarRunInfoTable
--
        hpnicfIfQoSTricolorCarRunInfoTable OBJECT-TYPE
            SYNTAX SEQUENCE OF HpnicfIfQoSTricolorCarRunInfoEntry
            MAX-ACCESS not-accessible
            STATUS current
            DESCRIPTION
                "A table of tricolor car statistic information."
            ::= { hpnicfIfQoSTricolorCarGroup 2 }

        hpnicfIfQoSTricolorCarRunInfoEntry OBJECT-TYPE
            SYNTAX HpnicfIfQoSTricolorCarRunInfoEntry
            MAX-ACCESS not-accessible
            STATUS current
            DESCRIPTION
                "Tricolor car statistic information entry."
            INDEX { ifIndex,
                    hpnicfIfQoSTricolorCarDirection,
                    hpnicfIfQoSTricolorCarType,
                    hpnicfIfQoSTricolorCarValue
                  }
            ::= { hpnicfIfQoSTricolorCarRunInfoTable 1 }

        HpnicfIfQoSTricolorCarRunInfoEntry ::=
            SEQUENCE
            {
                hpnicfIfQoSTricolorCarGreenPackets
                    Counter64,
                hpnicfIfQoSTricolorCarGreenBytes
                    Counter64,
                hpnicfIfQoSTricolorCarYellowPackets
                    Counter64,
                hpnicfIfQoSTricolorCarYellowBytes
                    Counter64,
                hpnicfIfQoSTricolorCarRedPackets
                    Counter64,
                hpnicfIfQoSTricolorCarRedBytes
                    Counter64
            }

        hpnicfIfQoSTricolorCarGreenPackets OBJECT-TYPE
            SYNTAX Counter64
            MAX-ACCESS read-only
            STATUS current
            DESCRIPTION
                "The number of green packets."
            ::= { hpnicfIfQoSTricolorCarRunInfoEntry 1 }

        hpnicfIfQoSTricolorCarGreenBytes OBJECT-TYPE
            SYNTAX Counter64
            MAX-ACCESS read-only
            STATUS current
            DESCRIPTION
                "The number of green bytes."
            ::= { hpnicfIfQoSTricolorCarRunInfoEntry 2 }

        hpnicfIfQoSTricolorCarYellowPackets OBJECT-TYPE
            SYNTAX Counter64
            MAX-ACCESS read-only
            STATUS current
            DESCRIPTION
                "The number of yellow packets."
            ::= { hpnicfIfQoSTricolorCarRunInfoEntry 3 }

        hpnicfIfQoSTricolorCarYellowBytes OBJECT-TYPE
            SYNTAX Counter64
            MAX-ACCESS read-only
            STATUS current
            DESCRIPTION
                "The number of yellow bytes."
            ::= { hpnicfIfQoSTricolorCarRunInfoEntry 4 }

        hpnicfIfQoSTricolorCarRedPackets OBJECT-TYPE
            SYNTAX Counter64
            MAX-ACCESS read-only
            STATUS current
            DESCRIPTION
                "The number of red packets."
            ::= { hpnicfIfQoSTricolorCarRunInfoEntry 5 }

        hpnicfIfQoSTricolorCarRedBytes OBJECT-TYPE
            SYNTAX Counter64
            MAX-ACCESS read-only
            STATUS current
            DESCRIPTION
                "The number of red bytes."
            ::= { hpnicfIfQoSTricolorCarRunInfoEntry 6 }
--
-- nodes of hpnicfIfQoSGTSObject
--
        hpnicfIfQoSGTSObjects OBJECT IDENTIFIER ::= { hpnicfIfQos2 5 }

        hpnicfIfQoSGTSConfigTable OBJECT-TYPE
            SYNTAX SEQUENCE OF HpnicfIfQoSGTSConfigEntry
            MAX-ACCESS not-accessible
            STATUS current
            DESCRIPTION
                "A table of generic traffic shaping information."
            ::= { hpnicfIfQoSGTSObjects 1 }

        hpnicfIfQoSGTSConfigEntry OBJECT-TYPE
            SYNTAX HpnicfIfQoSGTSConfigEntry
            MAX-ACCESS not-accessible
            STATUS current
            DESCRIPTION
                "Generic traffic shaping information entry."
            INDEX { ifIndex,
                    hpnicfIfQoSGTSClassRuleType,
                    hpnicfIfQoSGTSClassRuleValue
                  }
            ::= { hpnicfIfQoSGTSConfigTable 1 }

        HpnicfIfQoSGTSConfigEntry ::=
            SEQUENCE
            {
                hpnicfIfQoSGTSClassRuleType
                    INTEGER,
                hpnicfIfQoSGTSClassRuleValue
                    Integer32,
                hpnicfIfQoSGTSCir
                    Unsigned32,
                hpnicfIfQoSGTSCbs
                    Unsigned32,
                hpnicfIfQoSGTSEbs
                    Unsigned32,
                hpnicfIfQoSGTSQueueLength
                    Integer32,
                hpnicfIfQoSGTSConfigRowStatus
                    RowStatus,
                hpnicfIfQoSGTSPir
                    Unsigned32,
                hpnicfIfQoSGTSUnitType
                    INTEGER
            }

        hpnicfIfQoSGTSClassRuleType OBJECT-TYPE
            SYNTAX INTEGER
            {
                any(1),
                ipv4acl(2),
                ipv6acl(3),
                queue(4)
            }

            MAX-ACCESS not-accessible
            STATUS current
            DESCRIPTION
                "The index of the table,
                 which is the matching type for the packets on interface:
                 ipv4acl, ipv6acl, any, queue.
                "
            ::= { hpnicfIfQoSGTSConfigEntry 1 }

        hpnicfIfQoSGTSClassRuleValue OBJECT-TYPE
            SYNTAX Integer32 (0..2147483647)
            MAX-ACCESS not-accessible
            STATUS current
            DESCRIPTION
                "Value of type.
                 ipv4acl : 2000..5999
                 ipv6acl : 2000..42767
                 any : 0
                 queue : 0..7
                 "
            ::= { hpnicfIfQoSGTSConfigEntry 2 }

        hpnicfIfQoSGTSCir OBJECT-TYPE
            SYNTAX Unsigned32
            MAX-ACCESS read-create
            STATUS current
            DESCRIPTION
                "Committed Information Rate.  The unit of this parameter depends
                on the hpnicfIfQoSGTSUnitType node.
                +-----------+----------+------------+
                | Unit type | absolute | percent    |
                +-----------+----------+------------+
                | CIR unit  | kbps     | percentage |
                +-----------+----------+------------+
                "
            ::= { hpnicfIfQoSGTSConfigEntry 3 }

        hpnicfIfQoSGTSCbs OBJECT-TYPE
            SYNTAX Unsigned32
            MAX-ACCESS read-create
            STATUS current
            DESCRIPTION
                "Committed Burst Size.  The unit of this parameter depends
                on the hpnicfIfQoSGTSUnitType node.
                +-----------+----------+--------------+
                | Unit type | absolute | percent      |
                +-----------+----------+--------------+
                | CBS unit  | bytes    | milliseconds |
                +-----------+----------+--------------+
                "
            ::= { hpnicfIfQoSGTSConfigEntry 4 }

        hpnicfIfQoSGTSEbs OBJECT-TYPE
            SYNTAX Unsigned32
            MAX-ACCESS read-create
            STATUS current
            DESCRIPTION
                "Excess Burst Size.  The unit of this parameter depends
                on the hpnicfIfQoSGTSUnitType node.
                +-----------+----------+--------------+
                | Unit type | absolute | percent      |
                +-----------+----------+--------------+
                | EBS unit  | bytes    | milliseconds |
                +-----------+----------+--------------+
                "
            ::= { hpnicfIfQoSGTSConfigEntry 5 }

        hpnicfIfQoSGTSQueueLength OBJECT-TYPE
            SYNTAX Integer32
            MAX-ACCESS read-create
            STATUS current
            DESCRIPTION
                "The length of queue."
            ::= { hpnicfIfQoSGTSConfigEntry 6 }

        hpnicfIfQoSGTSConfigRowStatus OBJECT-TYPE
            SYNTAX RowStatus
            MAX-ACCESS read-create
            STATUS current
            DESCRIPTION
                "RowStatus."
            ::= { hpnicfIfQoSGTSConfigEntry 7 }

        hpnicfIfQoSGTSPir OBJECT-TYPE
            SYNTAX Unsigned32
            MAX-ACCESS read-create
            STATUS current
            DESCRIPTION
                "Peak information rate.  The unit of this parameter depends
                on the hpnicfIfQoSGTSUnitType node.
                +-----------+----------+------------+
                | Unit type | absolute | percent    |
                +-----------+----------+------------+
                | PIR unit  | kbps     | percentage |
                +-----------+----------+------------+
                "
            DEFVAL { 4294967295 }
            ::= { hpnicfIfQoSGTSConfigEntry 8 }

        hpnicfIfQoSGTSUnitType OBJECT-TYPE
            SYNTAX INTEGER
            {
                unitAbsolute(1),
                unitPercent(2)
            }
            MAX-ACCESS read-create
            STATUS current
            DESCRIPTION
                "Unit of token parameters.  If it is unitAbsolute, the token
                parameters are in kbps and bytes, and if it is unitPercent,
                the token parameters are in percentage and milliseconds."
            DEFVAL { unitAbsolute }
            ::= { hpnicfIfQoSGTSConfigEntry 9 }

--
-- nodes of hpnicfIfQoSGTSRunInfoTable
--
        hpnicfIfQoSGTSRunInfoTable OBJECT-TYPE
            SYNTAX SEQUENCE OF HpnicfIfQoSGTSRunInfoEntry
            MAX-ACCESS not-accessible
            STATUS current
            DESCRIPTION
                "A table of  generic traffic shaping's statistic information."
            ::= { hpnicfIfQoSGTSObjects 2 }

        hpnicfIfQoSGTSRunInfoEntry OBJECT-TYPE
            SYNTAX HpnicfIfQoSGTSRunInfoEntry
            MAX-ACCESS not-accessible
            STATUS current
            DESCRIPTION
                "Generic traffic shaping's statistic information entry."
            INDEX { ifIndex,
                    hpnicfIfQoSGTSClassRuleType,
                    hpnicfIfQoSGTSClassRuleValue
                  }
            ::= { hpnicfIfQoSGTSRunInfoTable 1 }

        HpnicfIfQoSGTSRunInfoEntry ::=
            SEQUENCE
            {
                hpnicfIfQoSGTSQueueSize
                    Integer32,
                hpnicfIfQoSGTSPassedPackets
                    Counter64,
                hpnicfIfQoSGTSPassedBytes
                    Counter64,
                hpnicfIfQoSGTSDiscardPackets
                    Counter64,
                hpnicfIfQoSGTSDiscardBytes
                    Counter64,
                hpnicfIfQoSGTSDelayedPackets
                    Counter64,
                hpnicfIfQoSGTSDelayedBytes
                    Counter64
            }

        hpnicfIfQoSGTSQueueSize OBJECT-TYPE
            SYNTAX Integer32
            MAX-ACCESS read-only
            STATUS current
            DESCRIPTION
                "The number of packets in the queue."
            ::= { hpnicfIfQoSGTSRunInfoEntry 1 }

        hpnicfIfQoSGTSPassedPackets OBJECT-TYPE
            SYNTAX Counter64
            MAX-ACCESS read-only
            STATUS current
            DESCRIPTION
                "The number of passed packets."
            ::= { hpnicfIfQoSGTSRunInfoEntry 2 }

        hpnicfIfQoSGTSPassedBytes OBJECT-TYPE
            SYNTAX Counter64
            MAX-ACCESS read-only
            STATUS current
            DESCRIPTION
                "The number of passed bytes."
            ::= { hpnicfIfQoSGTSRunInfoEntry 3 }

        hpnicfIfQoSGTSDiscardPackets OBJECT-TYPE
            SYNTAX Counter64
            MAX-ACCESS read-only
            STATUS current
            DESCRIPTION
                "The number of discard packets."
            ::= { hpnicfIfQoSGTSRunInfoEntry 4 }

        hpnicfIfQoSGTSDiscardBytes OBJECT-TYPE
            SYNTAX Counter64
            MAX-ACCESS read-only
            STATUS current
            DESCRIPTION
                "The number of discard bytes."
            ::= { hpnicfIfQoSGTSRunInfoEntry 5 }

        hpnicfIfQoSGTSDelayedPackets OBJECT-TYPE
            SYNTAX Counter64
            MAX-ACCESS read-only
            STATUS current
            DESCRIPTION
                "The number of delayed packets."
            ::= { hpnicfIfQoSGTSRunInfoEntry 6 }

        hpnicfIfQoSGTSDelayedBytes OBJECT-TYPE
            SYNTAX Counter64
            MAX-ACCESS read-only
            STATUS current
            DESCRIPTION
                "The number of delayed bytes."
            ::= { hpnicfIfQoSGTSRunInfoEntry 7 }
--
-- nodes of hpnicfIfQoSWREDObject
--
        hpnicfIfQoSWREDObjects OBJECT IDENTIFIER ::= { hpnicfIfQos2 6 }
--
-- nodes of WRED group
--
        hpnicfIfQoSWredGroupGroup OBJECT IDENTIFIER ::= { hpnicfIfQoSWREDObjects 1 }

        hpnicfIfQoSWredGroupNextIndex OBJECT-TYPE
            SYNTAX Integer32
            MAX-ACCESS read-only
            STATUS current
            DESCRIPTION
                "This object contains an appropriate value to be used for hpnicfIfQoSWredGroupIndex
                 when creating rows in the hpnicfIfQoSWredGroupTable.
                 Begin with 0.
                "
            ::= { hpnicfIfQoSWredGroupGroup 1 }
--
-- nodes of hpnicfIfQoSWredGroupTable
--
        hpnicfIfQoSWredGroupTable OBJECT-TYPE
            SYNTAX SEQUENCE OF HpnicfIfQoSWredGroupEntry
            MAX-ACCESS not-accessible
            STATUS current
            DESCRIPTION
                "A table of WRED group information."
            ::= { hpnicfIfQoSWredGroupGroup 2 }

        hpnicfIfQoSWredGroupEntry OBJECT-TYPE
            SYNTAX HpnicfIfQoSWredGroupEntry
            MAX-ACCESS not-accessible
            STATUS current
            DESCRIPTION
                "WRED group information."
            INDEX { hpnicfIfQoSWredGroupIndex }
            ::= { hpnicfIfQoSWredGroupTable 1 }

        HpnicfIfQoSWredGroupEntry ::=
            SEQUENCE
            {
                hpnicfIfQoSWredGroupIndex
                    Integer32,
                hpnicfIfQoSWredGroupName
                    OCTET STRING,
                hpnicfIfQoSWredGroupType
                    INTEGER,
                hpnicfIfQoSWredGroupWeightingConstant
                    Integer32,
                hpnicfIfQoSWredGroupRowStatus
                    RowStatus
            }

        hpnicfIfQoSWredGroupIndex OBJECT-TYPE
            SYNTAX Integer32 (0..256)
            MAX-ACCESS not-accessible
            STATUS current
            DESCRIPTION
                "WRED group index."
            ::= { hpnicfIfQoSWredGroupEntry 1 }

        hpnicfIfQoSWredGroupName OBJECT-TYPE
            SYNTAX OCTET STRING (SIZE(1..32))
            MAX-ACCESS read-create
            STATUS current
            DESCRIPTION
                "WRED group name."
            ::= { hpnicfIfQoSWredGroupEntry 2 }

        hpnicfIfQoSWredGroupType OBJECT-TYPE
            SYNTAX INTEGER
            {
                userdefined(0),
                dot1p(1),
                ippre(2),
                dscp(3),
                localpre(4),
                atmclp(5),
                frde(6),
                exp(7),
                queue(8),
                dropLevel(9)
            }
            MAX-ACCESS read-create
            STATUS current
            DESCRIPTION
                "Type of WRED group."
            ::= { hpnicfIfQoSWredGroupEntry 3 }

        hpnicfIfQoSWredGroupWeightingConstant OBJECT-TYPE
            SYNTAX Integer32 (1..15)
            MAX-ACCESS read-create
            STATUS current
            DESCRIPTION
                "Exponent for WRED calculates the average length of queue.
                 If 'hpnicfIfQoSWredGroupType' is 'queue', the object is ineffective.
                 So, it must use the object, which is 'hpnicfIfQoSWredGroupExponent' of
                 hpnicfIfQoSWredGroupContentTable, to indicate the exponent of
                 each queue of the queue WRED group."
            DEFVAL { 9 }
            ::= { hpnicfIfQoSWredGroupEntry 4 }

        hpnicfIfQoSWredGroupRowStatus OBJECT-TYPE
            SYNTAX RowStatus
            MAX-ACCESS read-create
            STATUS current
            DESCRIPTION
                "RowStatus."
            ::= { hpnicfIfQoSWredGroupEntry 6 }

--
-- nodes of hpnicfIfQoSWredGroupContentTable
--
        hpnicfIfQoSWredGroupContentTable OBJECT-TYPE
            SYNTAX SEQUENCE OF HpnicfIfQoSWredGroupContentEntry
            MAX-ACCESS not-accessible
            STATUS current
            DESCRIPTION
                "A table of priority WRED information."
            ::= { hpnicfIfQoSWredGroupGroup 3 }

        hpnicfIfQoSWredGroupContentEntry OBJECT-TYPE
            SYNTAX HpnicfIfQoSWredGroupContentEntry
            MAX-ACCESS not-accessible
            STATUS current
            DESCRIPTION
                "Priority WRED information entry."
            INDEX { hpnicfIfQoSWredGroupIndex,
                    hpnicfIfQoSWredGroupContentIndex,
                    hpnicfIfQoSWredGroupContentSubIndex  }
            ::= { hpnicfIfQoSWredGroupContentTable 1 }

        HpnicfIfQoSWredGroupContentEntry ::=
            SEQUENCE
            {
                hpnicfIfQoSWredGroupContentIndex
                    Integer32,
                hpnicfIfQoSWredGroupContentSubIndex
                    Integer32,
                hpnicfIfQoSWredLowLimit
                    Integer32,
                hpnicfIfQoSWredHighLimit
                    Integer32,
                hpnicfIfQoSWredDiscardProb
                    Integer32,
                hpnicfIfQoSWredGroupExponent
                    Integer32,
                hpnicfIfQoSWredRowStatus
                    RowStatus
            }

        hpnicfIfQoSWredGroupContentIndex OBJECT-TYPE
            SYNTAX Integer32 (0..63)
            MAX-ACCESS not-accessible
            STATUS current
            DESCRIPTION
                "The priority of a packet.
                 Different type of packet has different priority.
                 Type of priority    Range of priority
                 dot1p              0..7
                 ippre              0..7
                 dscp               0..63
                 atmclp             0..1
                 frde               0..1
                 exp                0..7
                 queue              0..7 ( defined by product )
                 dropLevel          0..2
                 "
            ::= { hpnicfIfQoSWredGroupContentEntry 1 }

        hpnicfIfQoSWredGroupContentSubIndex OBJECT-TYPE
            SYNTAX Integer32 (0..63)
            MAX-ACCESS not-accessible
            STATUS current
            DESCRIPTION
                "The sub index.
                 Different type of packet has different value.
                 Type of priority    Range of value
                 queue              0..2
                 other types : 0
                 "
            ::= { hpnicfIfQoSWredGroupContentEntry 2 }

        hpnicfIfQoSWredLowLimit OBJECT-TYPE
            SYNTAX Integer32
            MAX-ACCESS read-create
            STATUS current
            DESCRIPTION
                "Discard low limit."
            ::= { hpnicfIfQoSWredGroupContentEntry 3 }

        hpnicfIfQoSWredHighLimit OBJECT-TYPE
            SYNTAX Integer32
            MAX-ACCESS read-create
            STATUS current
            DESCRIPTION
                "Discard high limit."
            ::= { hpnicfIfQoSWredGroupContentEntry 4 }

        hpnicfIfQoSWredDiscardProb OBJECT-TYPE
            SYNTAX Integer32
            MAX-ACCESS read-create
            STATUS current
            DESCRIPTION
                "Discard probability."
            ::= { hpnicfIfQoSWredGroupContentEntry 5 }

        hpnicfIfQoSWredGroupExponent OBJECT-TYPE
            SYNTAX Integer32 (0..15)
            MAX-ACCESS read-create
            STATUS current
            DESCRIPTION
                "Exponent for WRED calculates the average length of queue.
                 Only 'hpnicfIfQoSWredGroupType' is 'queue', the object is effective.
                 This object is designed to indicate the exponent of
                 each queue of the queue WRED group.
                "
            DEFVAL { 9 }
            ::= { hpnicfIfQoSWredGroupContentEntry 6 }

        hpnicfIfQoSWredRowStatus OBJECT-TYPE
            SYNTAX RowStatus
            MAX-ACCESS read-create
            STATUS current
            DESCRIPTION
                "RowStatus."
            ::= { hpnicfIfQoSWredGroupContentEntry 7 }
--
-- nodes of hpnicfIfQoSWredApplyIfTable
--
        hpnicfIfQoSWredGroupApplyIfTable OBJECT-TYPE
            SYNTAX SEQUENCE OF HpnicfIfQoSWredGroupApplyIfEntry
            MAX-ACCESS not-accessible
            STATUS current
            DESCRIPTION
                "A table of WRED group applied interface information."
            ::= { hpnicfIfQoSWredGroupGroup 4 }

        hpnicfIfQoSWredGroupApplyIfEntry OBJECT-TYPE
            SYNTAX HpnicfIfQoSWredGroupApplyIfEntry
            MAX-ACCESS not-accessible
            STATUS current
            DESCRIPTION
                "WRED group applied interface information."
            INDEX { ifIndex }
            ::= { hpnicfIfQoSWredGroupApplyIfTable 1 }

        HpnicfIfQoSWredGroupApplyIfEntry ::=
            SEQUENCE
            {
                hpnicfIfQoSWredGroupApplyIndex
                    Integer32,
                hpnicfIfQoSWredGroupApplyName
                    OCTET STRING,
                hpnicfIfQoSWredGroupIfRowStatus
                    RowStatus
            }

        hpnicfIfQoSWredGroupApplyIndex OBJECT-TYPE
            SYNTAX Integer32 (0..256)
            MAX-ACCESS read-create
            STATUS current
            DESCRIPTION
                "WRED group index."
            ::= { hpnicfIfQoSWredGroupApplyIfEntry 1 }

        hpnicfIfQoSWredGroupApplyName OBJECT-TYPE
            SYNTAX OCTET STRING (SIZE(1..32))
            MAX-ACCESS read-only
            STATUS current
            DESCRIPTION
                "WRED group name."
            ::= { hpnicfIfQoSWredGroupApplyIfEntry 2 }

        hpnicfIfQoSWredGroupIfRowStatus OBJECT-TYPE
            SYNTAX RowStatus
            MAX-ACCESS read-create
            STATUS current
            DESCRIPTION
                "RowStatus."
            ::= { hpnicfIfQoSWredGroupApplyIfEntry 3 }
--
-- nodes of hpnicfIfQoSWredApplyIfStatisticTable
--
        hpnicfIfQoSWredApplyIfRunInfoTable OBJECT-TYPE
            SYNTAX SEQUENCE OF HpnicfIfQoSWredApplyIfRunInfoEntry
            MAX-ACCESS not-accessible
            STATUS current
            DESCRIPTION
                "A table of WRED statistic information."
            ::= { hpnicfIfQoSWredGroupGroup 5 }

        hpnicfIfQoSWredApplyIfRunInfoEntry  OBJECT-TYPE
            SYNTAX HpnicfIfQoSWredApplyIfRunInfoEntry
            MAX-ACCESS not-accessible
            STATUS current
            DESCRIPTION
                "WRED statistic information."
            INDEX { ifIndex,
                    hpnicfIfQoSWredGroupIndex,
                    hpnicfIfQoSWredGroupContentIndex,
                    hpnicfIfQoSWredGroupContentSubIndex
                  }
            ::= { hpnicfIfQoSWredApplyIfRunInfoTable 1 }

        HpnicfIfQoSWredApplyIfRunInfoEntry ::=
            SEQUENCE
            {
                hpnicfIfQoSWredPreRandomDropNum
                    Counter64,
                hpnicfIfQoSWredPreTailDropNum
                    Counter64
            }

        hpnicfIfQoSWredPreRandomDropNum OBJECT-TYPE
            SYNTAX Counter64
            MAX-ACCESS read-only
            STATUS current
            DESCRIPTION
                "The number of random drop."
            ::= { hpnicfIfQoSWredApplyIfRunInfoEntry 1 }

        hpnicfIfQoSWredPreTailDropNum OBJECT-TYPE
            SYNTAX Counter64
            MAX-ACCESS read-only
            STATUS current
            DESCRIPTION
                "The number of tail drop."
            ::= { hpnicfIfQoSWredApplyIfRunInfoEntry 2 }
--
-- nodes of hpnicfIfQoSPortWREDGroup
--
        hpnicfIfQoSPortWredGroup OBJECT IDENTIFIER ::= { hpnicfIfQoSWREDObjects 2 }

        hpnicfIfQoSPortWredWeightConstantTable OBJECT-TYPE
            SYNTAX SEQUENCE OF HpnicfIfQoSPortWREDWeightConstantEntry
            MAX-ACCESS not-accessible
            STATUS current
            DESCRIPTION
                "A table of port WRED configuration information."
            ::= { hpnicfIfQoSPortWredGroup 1 }

        hpnicfIfQoSPortWredWeightConstantEntry OBJECT-TYPE
            SYNTAX HpnicfIfQoSPortWREDWeightConstantEntry
            MAX-ACCESS not-accessible
            STATUS current
            DESCRIPTION
                "Port WRED configuration information entry."
            INDEX { ifIndex }
            ::= { hpnicfIfQoSPortWredWeightConstantTable 1 }

        HpnicfIfQoSPortWREDWeightConstantEntry ::=
            SEQUENCE
            {
                hpnicfIfQoSPortWredEnable
                    TruthValue,
                hpnicfIfQoSPortWredWeightConstant
                    Integer32,
                hpnicfIfQoSPortWredWeightConstantRowStatus
                    RowStatus
            }

        hpnicfIfQoSPortWredEnable OBJECT-TYPE
            SYNTAX TruthValue
            MAX-ACCESS read-create
            STATUS current
            DESCRIPTION
                "The object is used to enable or disable WRED function of the port.
                 true: Enable WRED function of a port.
                 false: Disable WRED function of a port.
                "
            ::= { hpnicfIfQoSPortWredWeightConstantEntry 1 }

        hpnicfIfQoSPortWredWeightConstant OBJECT-TYPE
            SYNTAX Integer32 (1..16)
            MAX-ACCESS read-create
            STATUS current
            DESCRIPTION
                "Weight constant."
            ::= { hpnicfIfQoSPortWredWeightConstantEntry 2 }

        hpnicfIfQoSPortWredWeightConstantRowStatus OBJECT-TYPE
            SYNTAX RowStatus
            MAX-ACCESS read-create
            STATUS current
            DESCRIPTION
                "RowStatus."
            ::= { hpnicfIfQoSPortWredWeightConstantEntry 3 }
--
-- notes of hpnicfIfQoSPortWredPreConfigTable
--
        hpnicfIfQoSPortWredPreConfigTable OBJECT-TYPE
            SYNTAX SEQUENCE OF HpnicfIfQoSPortWREDPreConfigEntry
            MAX-ACCESS not-accessible
            STATUS current
            DESCRIPTION
                "A table of weighted random early detect precedence configuration information."
            ::= { hpnicfIfQoSPortWredGroup 2 }

        hpnicfIfQoSPortWredPreConfigEntry OBJECT-TYPE
            SYNTAX HpnicfIfQoSPortWREDPreConfigEntry
            MAX-ACCESS not-accessible
            STATUS current
            DESCRIPTION
                "Weighted random early detect precedence configuration information entry."
            INDEX { ifIndex, hpnicfIfQoSPortWredPreID }
            ::= { hpnicfIfQoSPortWredPreConfigTable 1 }

        HpnicfIfQoSPortWREDPreConfigEntry ::=
            SEQUENCE
            {
                hpnicfIfQoSPortWredPreID
                    Integer32,
                hpnicfIfQoSPortWredPreLowLimit
                    Integer32,
                hpnicfIfQoSPortWredPreHighLimit
                    Integer32,
                hpnicfIfQoSPortWredPreDiscardProbability
                    Integer32,
                hpnicfIfQoSPortWredPreRowStatus
                    RowStatus
            }

        hpnicfIfQoSPortWredPreID OBJECT-TYPE
            SYNTAX Integer32
            MAX-ACCESS not-accessible
            STATUS current
            DESCRIPTION
                "IP precedence, from 0 to 7."
            ::= { hpnicfIfQoSPortWredPreConfigEntry 1 }

        hpnicfIfQoSPortWredPreLowLimit OBJECT-TYPE
            SYNTAX Integer32
            MAX-ACCESS read-create
            STATUS current
            DESCRIPTION
                "Low Limit(number of packets)"
            ::= { hpnicfIfQoSPortWredPreConfigEntry 2 }

        hpnicfIfQoSPortWredPreHighLimit OBJECT-TYPE
            SYNTAX Integer32
            MAX-ACCESS read-create
            STATUS current
            DESCRIPTION
                "High limit(number of packets)"
            ::= { hpnicfIfQoSPortWredPreConfigEntry 3 }

        hpnicfIfQoSPortWredPreDiscardProbability OBJECT-TYPE
            SYNTAX Integer32
            MAX-ACCESS read-create
            STATUS current
            DESCRIPTION
                "Discard probability denominator"
            ::= { hpnicfIfQoSPortWredPreConfigEntry 4 }

        hpnicfIfQoSPortWredPreRowStatus OBJECT-TYPE
            SYNTAX RowStatus
            MAX-ACCESS read-create
            STATUS current
            DESCRIPTION
                "RowStatus."
            ::= { hpnicfIfQoSPortWredPreConfigEntry 5 }

--
-- nodes of hpnicfIfQoSPortWredRunInfoTable
--
        hpnicfIfQoSPortWredRunInfoTable OBJECT-TYPE
            SYNTAX SEQUENCE OF HpnicfIfQoSPortWREDRunInfoEntry
            MAX-ACCESS not-accessible
            STATUS current
            DESCRIPTION
                "A table of WRED statistic information."
            ::= { hpnicfIfQoSPortWredGroup 3 }

        hpnicfIfQoSPortWredRunInfoEntry OBJECT-TYPE
            SYNTAX HpnicfIfQoSPortWREDRunInfoEntry
            MAX-ACCESS not-accessible
            STATUS current
            DESCRIPTION
                "WRED statistic information entry."
            INDEX { ifIndex, hpnicfIfQoSPortWredPreID }
            ::= { hpnicfIfQoSPortWredRunInfoTable 1 }

        HpnicfIfQoSPortWREDRunInfoEntry ::=
            SEQUENCE
            {
                hpnicfIfQoSWREDTailDropNum
                    Counter64,
                hpnicfIfQoSWREDRandomDropNum
                    Counter64
            }

        hpnicfIfQoSWREDTailDropNum OBJECT-TYPE
            SYNTAX Counter64
            MAX-ACCESS read-only
            STATUS current
            DESCRIPTION
                "The number of tail drop."
            ::= { hpnicfIfQoSPortWredRunInfoEntry 1 }

        hpnicfIfQoSWREDRandomDropNum OBJECT-TYPE
            SYNTAX Counter64
            MAX-ACCESS read-only
            STATUS current
            DESCRIPTION
                "The number of random drop."
            ::= { hpnicfIfQoSPortWredRunInfoEntry 2 }

--
-- nodes of hpnicfIfQoSPortPriorityObject
--

        hpnicfIfQoSPortPriorityObjects OBJECT IDENTIFIER ::= { hpnicfIfQos2 7 }

        hpnicfIfQoSPortPriorityConfigGroup OBJECT IDENTIFIER ::= { hpnicfIfQoSPortPriorityObjects 1 }

        hpnicfIfQoSPortPriorityTable OBJECT-TYPE
            SYNTAX SEQUENCE OF HpnicfIfQoSPortPriorityEntry
            MAX-ACCESS not-accessible
            STATUS current
            DESCRIPTION
                "A table of port priority information."
            ::= { hpnicfIfQoSPortPriorityConfigGroup 1 }

        hpnicfIfQoSPortPriorityEntry OBJECT-TYPE
            SYNTAX HpnicfIfQoSPortPriorityEntry
            MAX-ACCESS not-accessible
            STATUS current
            DESCRIPTION
                "Port priority information entry."
            INDEX { ifIndex }
            ::= { hpnicfIfQoSPortPriorityTable 1 }

        HpnicfIfQoSPortPriorityEntry    ::=
            SEQUENCE
            {
                hpnicfIfQoSPortPriorityValue
                    Integer32
            }

        hpnicfIfQoSPortPriorityValue OBJECT-TYPE
            SYNTAX Integer32 (0..7)
            MAX-ACCESS read-write
            STATUS current
            DESCRIPTION
                "The priority of a port."
            DEFVAL { 0 }
            ::= { hpnicfIfQoSPortPriorityEntry 1 }
--
-- nodes of hpnicfIfQoSPortPirorityTrustTable
--
        hpnicfIfQoSPortPirorityTrustTable OBJECT-TYPE
            SYNTAX SEQUENCE OF HpnicfIfQoSPortPirorityTrustEntry
            MAX-ACCESS not-accessible
            STATUS current
            DESCRIPTION
                "A table of each port's trusted priority information."
            ::= { hpnicfIfQoSPortPriorityConfigGroup 2 }

        hpnicfIfQoSPortPirorityTrustEntry OBJECT-TYPE
            SYNTAX HpnicfIfQoSPortPirorityTrustEntry
            MAX-ACCESS not-accessible
            STATUS current
            DESCRIPTION
                "Per-port trusted priority information entry."
            INDEX { ifIndex }
            ::= { hpnicfIfQoSPortPirorityTrustTable 1 }

        HpnicfIfQoSPortPirorityTrustEntry ::=
            SEQUENCE
            {
                hpnicfIfQoSPortPriorityTrustTrustType
                    INTEGER,
                hpnicfIfQoSPortPriorityTrustOvercastType
                    INTEGER
            }

        hpnicfIfQoSPortPriorityTrustTrustType OBJECT-TYPE
            SYNTAX INTEGER
            {
                untrust(1),
                dot1p(2),
                dscp(3),
                exp(4),
                ipPrecedence(5),
                dot11e(6),
                auto(7)
            }
            MAX-ACCESS read-write
            STATUS current
            DESCRIPTION
                "Trusted priority type of a port."
            DEFVAL { untrust }
            ::= { hpnicfIfQoSPortPirorityTrustEntry 1 }

        hpnicfIfQoSPortPriorityTrustOvercastType OBJECT-TYPE
            SYNTAX INTEGER
            {
                noOvercast(1),
                overcastDSCP(2),
                overcastCOS(3),
                overcast(4)
            }
            MAX-ACCESS read-write
            STATUS current
            DESCRIPTION
                "The overcast type."
            DEFVAL { noOvercast }
            ::= { hpnicfIfQoSPortPirorityTrustEntry 2 }
--
-- nodes of map object
--
        hpnicfIfQoSMapObjects OBJECT IDENTIFIER ::= { hpnicfIfQos2 9 }
--
-- nodes of hpnicfIfQoSMapConfigGroup
--
        hpnicfIfQoSPriMapConfigGroup OBJECT IDENTIFIER ::= { hpnicfIfQoSMapObjects 1 }

        hpnicfIfQoSPriMapGroupNextIndex OBJECT-TYPE
            SYNTAX Integer32
            MAX-ACCESS read-only
            STATUS current
            DESCRIPTION
                "This object contains an appropriate value to be used for hpnicfIfQoSPriMapGroupIndex
                 when creating rows in the hpnicfIfQoSPriMapGroupTable.
                 Begin with 64.
                "
            ::= { hpnicfIfQoSPriMapConfigGroup 1 }
--
-- nodes of hpnicfIfQoSPriMapConfigTable
--
        hpnicfIfQoSPriMapGroupTable OBJECT-TYPE
            SYNTAX SEQUENCE OF HpnicfIfQoSPriMapGroupEntry
            MAX-ACCESS not-accessible
            STATUS current
            DESCRIPTION
                "A table of map group information."
            ::= { hpnicfIfQoSPriMapConfigGroup 2 }

        hpnicfIfQoSPriMapGroupEntry OBJECT-TYPE
            SYNTAX HpnicfIfQoSPriMapGroupEntry
            MAX-ACCESS not-accessible
            STATUS current
            DESCRIPTION
                "Map group information entry."
            INDEX { hpnicfIfQoSPriMapGroupIndex  }
            ::= { hpnicfIfQoSPriMapGroupTable 1 }

        HpnicfIfQoSPriMapGroupEntry ::=
            SEQUENCE
            {
                hpnicfIfQoSPriMapGroupIndex
                    Integer32,
                hpnicfIfQoSPriMapGroupType
                    INTEGER,
                hpnicfIfQoSPriMapGroupName
                    OCTET STRING,
                hpnicfIfQoSPriMapGroupRowStatus
                    RowStatus
            }

        hpnicfIfQoSPriMapGroupIndex OBJECT-TYPE
            SYNTAX Integer32
            MAX-ACCESS not-accessible
            STATUS current
            DESCRIPTION
                "The index of map, which are defined by system and user.
                 The index of system defined map is 1 to 9.
                 System defined map-name/map-index pairs like this:
                 Map-index    Map-name
                 1            dot1p-dp
                 2            dot1p-dscp
                 3            dot1p-lp
                 4            dscp-dot1p
                 5            dscp-dp
                 6            dscp-dscp
                 7            dscp-lp
                 8            exp-dp
                 9            exp-lp
                "
            ::= { hpnicfIfQoSPriMapGroupEntry 1 }

        hpnicfIfQoSPriMapGroupType OBJECT-TYPE
            SYNTAX INTEGER
            {
                userdefined(1),
                dot1p-dp(2),
                dot1p-dscp(3),
                dot1p-lp(4),
                dscp-dot1p(5),
                dscp-dp(6),
                dscp-dscp(7),
                dscp-lp(8),
                exp-dp(9),
                exp-lp(10)
            }
            MAX-ACCESS read-create
            STATUS current
            DESCRIPTION
                "The type of map group."
            ::= { hpnicfIfQoSPriMapGroupEntry 2 }

        hpnicfIfQoSPriMapGroupName OBJECT-TYPE
            SYNTAX OCTET STRING (SIZE(1..32))
            MAX-ACCESS read-create
            STATUS current
            DESCRIPTION
                "The name of map group."
            ::= { hpnicfIfQoSPriMapGroupEntry 3 }

        hpnicfIfQoSPriMapGroupRowStatus OBJECT-TYPE
            SYNTAX RowStatus
            MAX-ACCESS read-create
            STATUS current
            DESCRIPTION
                "RowStatus."
            ::= { hpnicfIfQoSPriMapGroupEntry 4 }

--
-- nodes of hpnicfIfQoSPriMapContentTable
--
        hpnicfIfQoSPriMapContentTable OBJECT-TYPE
            SYNTAX SEQUENCE OF HpnicfIfQoSPriMapContentEntry
            MAX-ACCESS not-accessible
            STATUS current
            DESCRIPTION
                "A table of priority map configuration information."
            ::= { hpnicfIfQoSPriMapConfigGroup 3 }

        hpnicfIfQoSPriMapContentEntry OBJECT-TYPE
            SYNTAX HpnicfIfQoSPriMapContentEntry
            MAX-ACCESS not-accessible
            STATUS current
            DESCRIPTION
                "Priority map configuration information entry."
            INDEX { hpnicfIfQoSPriMapGroupIndex, hpnicfIfQoSPriMapGroupImportValue }
            ::= { hpnicfIfQoSPriMapContentTable 1 }

        HpnicfIfQoSPriMapContentEntry ::=
            SEQUENCE
            {
                hpnicfIfQoSPriMapGroupImportValue
                    Integer32,
                hpnicfIfQoSPriMapGroupExportValue
                    Integer32,
                hpnicfIfQoSPriMapContentRowStatus
                    RowStatus
            }

        hpnicfIfQoSPriMapGroupImportValue OBJECT-TYPE
            SYNTAX Integer32 (0..63)
            MAX-ACCESS not-accessible
            STATUS current
            DESCRIPTION
                "Priority map table import value list.
                 Different map has different hpnicfIfQoSPriMapConfigImportValue.
                 Map-name       Range of hpnicfIfQoSPriMapConfigImportValue
                 dot1p-dp       (0..7)
                 dot1p-dscp     (0..7)
                 dot1p-lp       (0..7)
                 dscp-dot1p     (0..63)
                 dscp-dp        (0..63)
                 dscp-dscp      (0..63)
                 dscp-lp(7)     (0..63)
                 exp-dp(8)      (0..7)
                 exp-lp         (0..7)
                "
            ::= { hpnicfIfQoSPriMapContentEntry 1 }

        hpnicfIfQoSPriMapGroupExportValue OBJECT-TYPE
            SYNTAX Integer32 (0..63)
            MAX-ACCESS read-create
            STATUS current
            DESCRIPTION
                "Priority map table output.
                 Different map has different hpnicfIfQoSPriMapGroupExportValue.
                 dot1p-dp:   0..7
                 dot1p-dscp: 0..63
                 dot1p-lp:   0..7
                 dscp-dot1p: 0..7
                 dscp-dp:    0..7
                 dscp-dscp:  0..63
                 dscp-lp:    0..7
                 exp-dp:     0..7
                 exp-lp:     0..7
                "
            ::= { hpnicfIfQoSPriMapContentEntry 2 }

        hpnicfIfQoSPriMapContentRowStatus OBJECT-TYPE
            SYNTAX RowStatus
            MAX-ACCESS read-create
            STATUS current
            DESCRIPTION
                "RowStatus."
            ::= { hpnicfIfQoSPriMapContentEntry 3 }

--
-- nodes of hpnicfIfQoSPrePriMapTable
--
        hpnicfIfQoSPrePriMapTable OBJECT-TYPE
            SYNTAX SEQUENCE OF HpnicfIfQoSPrePriMapEntry
            MAX-ACCESS not-accessible
            STATUS current
            DESCRIPTION
                "Pre-defined priority mapping table information."
            ::= { hpnicfIfQoSPriMapConfigGroup 4 }

        hpnicfIfQoSPrePriMapEntry OBJECT-TYPE
            SYNTAX HpnicfIfQoSPrePriMapEntry
            MAX-ACCESS not-accessible
            STATUS current
            DESCRIPTION
                "Pre-defined priority mapping table entry."
            INDEX
            {
                hpnicfIfQoSPrePriMapTableType,
                hpnicfIfQoSPrePriMapTableColor,
                hpnicfIfQoSPrePriMapTableDirection,
                hpnicfIfQoSPrePriMapTableImportValue
            }
            ::= { hpnicfIfQoSPrePriMapTable 1 }

        HpnicfIfQoSPrePriMapEntry ::=
            SEQUENCE
            {
                hpnicfIfQoSPrePriMapTableType
                    INTEGER,
                hpnicfIfQoSPrePriMapTableColor
                    INTEGER,
                hpnicfIfQoSPrePriMapTableDirection
                    INTEGER,
                hpnicfIfQoSPrePriMapTableImportValue
                    Integer32,
                hpnicfIfQoSPrePriMapTableExportValue
                    Integer32
            }

        hpnicfIfQoSPrePriMapTableType OBJECT-TYPE
            SYNTAX INTEGER
            {
                dot1pToLp(1),
                dot1pToDp(2),
                expToLp(3),
                dscpToLp(4),
                expToDp(5),
                dscpToDp(6),
                dscpToDot1p(7),
                dot1pToDscp(8),
                dscpToDscp(9),
                dscpToExp(10),
                expToDscp(11),
                expToDot1p(12),
                expToExp(13),
                lpToDot1p(14),
                dot1pToRpr(15),
                dscpToRpr(16),
                expToRpr(17),
                ippreToRpr(18),
                upToDot1p(19),
                upToDscp(20),
                upToExp(21),
                upToDp(22),
                upToLp(23),
                upToRpr(24),
                upToFc(25),
                lpTodscp(26),
                dot11eToLp(27),
                lpToDot11e(28),
                lpToLp(29),
                dot1pToExp(30),
                lpToExp(31),
                lpToDp(32),
                upToUp(33),
                dot1pToDot1p(34)
            }
            MAX-ACCESS not-accessible
            STATUS current
            DESCRIPTION
                "The type of pre-defined priority mapping table."
            ::= { hpnicfIfQoSPrePriMapEntry 1 }

        hpnicfIfQoSPrePriMapTableColor OBJECT-TYPE
            SYNTAX INTEGER
            {
                noColor(1),
                green(2),
                yellow(3),
                red(4)
            }
            MAX-ACCESS not-accessible
            STATUS current
            DESCRIPTION
                "The color of pre-defined priority mapping table."
            ::= { hpnicfIfQoSPrePriMapEntry 2 }

        hpnicfIfQoSPrePriMapTableDirection OBJECT-TYPE
            SYNTAX INTEGER
            {
                noDirection(1),
                inbound(2),
                outbound(3)
            }
            MAX-ACCESS not-accessible
            STATUS current
            DESCRIPTION
                "The direction of pre-defined priority mapping table."
            ::= { hpnicfIfQoSPrePriMapEntry 3 }

        hpnicfIfQoSPrePriMapTableImportValue OBJECT-TYPE
            SYNTAX Integer32 (0..63)
            MAX-ACCESS not-accessible
            STATUS current
            DESCRIPTION
                "Input value of priority mapping table.
                 Different priority has different hpnicfIfQoSPrePriMapTableImportValue.
                 Priority-type  Range of hpnicfIfQoSPrePriMapTableImportValue
                 dot1p          (0..7)
                 dscp           (0..63)
                 lp             (0..7)
                 exp            (0..7)
                 ipPrecedence   (0..7)
                 up             (0..7)
                 dot11e         (0..7)
                "
            ::= { hpnicfIfQoSPrePriMapEntry 4 }

        hpnicfIfQoSPrePriMapTableExportValue OBJECT-TYPE
            SYNTAX Integer32 (0..63)
            MAX-ACCESS read-write
            STATUS current
            DESCRIPTION
                "Output value of priority mapping table.
                 Different priority has different hpnicfIfQoSPrePriMapTableExportValue.
                 Priority-type  Range of hpnicfIfQoSPrePriMapTableExportValue
                 dot1p          (0..7)
                 dscp           (0..63)
                 lp             (0..7)
                 exp            (0..7)
                 ipPrecedence   (0..7)
                 up             (0..7)
                 dp             (0..2)
                 fc             (0..7)
                 rpr            (0..2)
                "
            ::= { hpnicfIfQoSPrePriMapEntry 5 }

--
-- nodes of L3 plus object
--
        hpnicfIfQoSL3PlusObjects OBJECT IDENTIFIER ::= { hpnicfIfQos2 10 }
--
-- nodes of hpnicfIfQoSPortBindingGroup
--
        hpnicfIfQoSPortBindingGroup OBJECT IDENTIFIER ::= { hpnicfIfQoSL3PlusObjects 1 }

        hpnicfIfQoSPortBindingTable OBJECT-TYPE
            SYNTAX SEQUENCE OF HpnicfIfQoSPortBindingEntry
            MAX-ACCESS not-accessible
            STATUS current
            DESCRIPTION
                "A table of EACL sub-interface binding information
                 for L3+ board ."
            ::= { hpnicfIfQoSPortBindingGroup 1 }

        hpnicfIfQoSPortBindingEntry OBJECT-TYPE
            SYNTAX HpnicfIfQoSPortBindingEntry
            MAX-ACCESS not-accessible
            STATUS current
            DESCRIPTION
                "Binding information entry."
            INDEX { ifIndex }
            ::= { hpnicfIfQoSPortBindingTable 1 }

        HpnicfIfQoSPortBindingEntry ::=
            SEQUENCE
            {
                hpnicfIfQoSBindingIf
                    Integer32,
                hpnicfIfQoSBindingRowStatus
                    RowStatus
            }

        hpnicfIfQoSBindingIf OBJECT-TYPE
            SYNTAX Integer32
            MAX-ACCESS read-create
            STATUS current
            DESCRIPTION
                "The binding interface."
            ::= { hpnicfIfQoSPortBindingEntry 1 }

        hpnicfIfQoSBindingRowStatus OBJECT-TYPE
            SYNTAX RowStatus
            MAX-ACCESS read-create
            STATUS current
            DESCRIPTION
                "RowStatus"
            ::= { hpnicfIfQoSPortBindingEntry 2 }

--
-- node of hpnicfQoSTraStaObjects
--
        hpnicfQoSTraStaObjects OBJECT IDENTIFIER ::= { hpnicfIfQos2 11 }
--
-- nodes of hpnicfQoSTraStaConfigGroup
--
        hpnicfQoSTraStaConfigGroup OBJECT IDENTIFIER ::= { hpnicfQoSTraStaObjects 1 }

        hpnicfQoSIfTraStaConfigInfoTable OBJECT-TYPE
            SYNTAX SEQUENCE OF HpnicfQoSIfTraStaConfigInfoEntry
            MAX-ACCESS not-accessible
            STATUS current
            DESCRIPTION
                "A table of traffic statistics configuration information."
            ::= { hpnicfQoSTraStaConfigGroup 1 }

        hpnicfQoSIfTraStaConfigInfoEntry OBJECT-TYPE
            SYNTAX HpnicfQoSIfTraStaConfigInfoEntry
            MAX-ACCESS not-accessible
            STATUS current
            DESCRIPTION
                "An entry of interface traffic statistics configuration information."
            INDEX { ifIndex, hpnicfQoSIfTraStaConfigDirection }
            ::= { hpnicfQoSIfTraStaConfigInfoTable 1 }

        HpnicfQoSIfTraStaConfigInfoEntry ::=
            SEQUENCE
            {
                hpnicfQoSIfTraStaConfigDirection
                    Direction,
                hpnicfQoSIfTraStaConfigQueue
                    OCTET STRING,
                hpnicfQoSIfTraStaConfigDot1p
                    OCTET STRING,
                hpnicfQoSIfTraStaConfigDscp
                    OCTET STRING,
                hpnicfQoSIfTraStaConfigVlan
                    OCTET STRING,
                hpnicfQoSIfTraStaConfigStatus
                    RowStatus
            }

        hpnicfQoSIfTraStaConfigDirection OBJECT-TYPE
            SYNTAX Direction
            MAX-ACCESS not-accessible
            STATUS current
            DESCRIPTION "The direction of the traffic statistics."
            ::= { hpnicfQoSIfTraStaConfigInfoEntry 1 }

        hpnicfQoSIfTraStaConfigQueue OBJECT-TYPE
            SYNTAX OCTET STRING (SIZE (1))
            MAX-ACCESS read-create
            STATUS current
            DESCRIPTION "The bitmap of Queue ID.
                        The octet specifies queues 0 through 7.  If a bit has
                        a value of '1', the corresponding queue is configured
                        in the set of Queues; if a bit has a value of '0',
                        the corresponding queue is not configured."
            ::= { hpnicfQoSIfTraStaConfigInfoEntry 2 }

        hpnicfQoSIfTraStaConfigDot1p OBJECT-TYPE
            SYNTAX OCTET STRING (SIZE (1))
            MAX-ACCESS read-create
            STATUS current
            DESCRIPTION "The bitmap of Dot1p value.
                        The octet specifies Dot1p values 0 through 7.  If a bit
                        has a value of '1', the corresponding Dot1p value is
                        configured in the set of Dot1p values; if a bit has a
                        value of '0', the corresponding Dot1p value is not
                        configured."
            ::= { hpnicfQoSIfTraStaConfigInfoEntry 3 }

        hpnicfQoSIfTraStaConfigDscp OBJECT-TYPE
            SYNTAX OCTET STRING (SIZE (8))
            MAX-ACCESS read-create
            STATUS current
            DESCRIPTION "The bitmap of Dscp value.
                        Each octet within this value specifies a set of
                        eight Dscp values, with the first octet specifying
                        Dscp values 0 through 7, the second octet specifying
                        Dscp values 8 through 15, etc.  If a bit has a value
                        of '1', the corresponding Dscp value is configured
                        in the set of Dscp values; if a bit has a value of
                        '0', the corresponding Dscp value is not configured."
            ::= { hpnicfQoSIfTraStaConfigInfoEntry 4 }

        hpnicfQoSIfTraStaConfigVlan OBJECT-TYPE
            SYNTAX OCTET STRING (SIZE (512))
            MAX-ACCESS read-create
            STATUS current
            DESCRIPTION "The bitmap of VLAN ID.
                        Each octet within this value specifies a set of
                        eight VLANs, with the first octet specifying
                        VLANs 0 through 7, the second octet specifying VLANs
                        8 through 15, etc.  If a bit has a value of '1', the
                        corresponding VLAN is configured in the set of VLANs;
                        if a bit has a value of '0', the corresponding VLAN
                        is not configured."
            ::= { hpnicfQoSIfTraStaConfigInfoEntry 5 }

        hpnicfQoSIfTraStaConfigStatus OBJECT-TYPE
            SYNTAX RowStatus
            MAX-ACCESS read-create
            STATUS current
            DESCRIPTION "The row status of this table entry."
            ::= { hpnicfQoSIfTraStaConfigInfoEntry 6 }


--
-- nodes of hpnicfQoSTraStaRunGroup
--
        hpnicfQoSTraStaRunGroup OBJECT IDENTIFIER ::= { hpnicfQoSTraStaObjects 2 }

        hpnicfQoSIfTraStaRunInfoTable OBJECT-TYPE
            SYNTAX SEQUENCE OF HpnicfQoSIfTraStaRunInfoEntry
            MAX-ACCESS not-accessible
            STATUS current
            DESCRIPTION
                "A table of traffic statistics running information."
            ::= { hpnicfQoSTraStaRunGroup 1 }

        hpnicfQoSIfTraStaRunInfoEntry OBJECT-TYPE
            SYNTAX HpnicfQoSIfTraStaRunInfoEntry
            MAX-ACCESS not-accessible
            STATUS current
            DESCRIPTION
                "An entry of interface traffic statistics running information."
            INDEX { ifIndex,
                    hpnicfQoSIfTraStaRunObjectType,
                    hpnicfQoSIfTraStaRunObjectValue,
                    hpnicfQoSIfTraStaRunDirection }
            ::= { hpnicfQoSIfTraStaRunInfoTable 1 }

        HpnicfQoSIfTraStaRunInfoEntry ::=
            SEQUENCE
            {
                hpnicfQoSIfTraStaRunObjectType
                    INTEGER,
                hpnicfQoSIfTraStaRunObjectValue
                    Integer32,
                hpnicfQoSIfTraStaRunDirection
                    Direction,
                hpnicfQoSIfTraStaRunPassPackets
                    Counter64,
                hpnicfQoSIfTraStaRunDropPackets
                    Counter64,
                hpnicfQoSIfTraStaRunPassBytes
                    Counter64,
                hpnicfQoSIfTraStaRunDropBytes
                    Counter64,
                hpnicfQoSIfTraStaRunPassPPS
                    Counter64,
                hpnicfQoSIfTraStaRunPassBPS
                    Counter64
            }

        hpnicfQoSIfTraStaRunObjectType OBJECT-TYPE
            SYNTAX INTEGER
            {
                queue(1),
                dot1p(2),
                dscp(3),
                vlanID(4)
            }
            MAX-ACCESS not-accessible
            STATUS current
            DESCRIPTION
                "Type of statistics object."
            ::= { hpnicfQoSIfTraStaRunInfoEntry 1 }

        hpnicfQoSIfTraStaRunObjectValue OBJECT-TYPE
            SYNTAX Integer32
            MAX-ACCESS not-accessible
            STATUS current
            DESCRIPTION
                "Value range for the object type:
                 for Queue: 0~7
                 for Dot1p: 0~7
                 for Dscp: 0~63
                 for VlanID: 1~4094
                 "
            ::= { hpnicfQoSIfTraStaRunInfoEntry 2 }

        hpnicfQoSIfTraStaRunDirection OBJECT-TYPE
            SYNTAX Direction
            MAX-ACCESS not-accessible
            STATUS current
            DESCRIPTION
                "The direction of the traffic statistics."
            ::= { hpnicfQoSIfTraStaRunInfoEntry 3 }

        hpnicfQoSIfTraStaRunPassPackets OBJECT-TYPE
            SYNTAX Counter64
            MAX-ACCESS read-only
            STATUS current
            DESCRIPTION
                "Number of passed packets."
            ::= { hpnicfQoSIfTraStaRunInfoEntry 4 }

        hpnicfQoSIfTraStaRunDropPackets OBJECT-TYPE
            SYNTAX Counter64
            MAX-ACCESS read-only
            STATUS current
            DESCRIPTION
                "Number of dropped packets."
            ::= { hpnicfQoSIfTraStaRunInfoEntry 5 }

        hpnicfQoSIfTraStaRunPassBytes OBJECT-TYPE
            SYNTAX Counter64
            MAX-ACCESS read-only
            STATUS current
            DESCRIPTION
                "Number of passed bytes."
            ::= { hpnicfQoSIfTraStaRunInfoEntry 6 }

        hpnicfQoSIfTraStaRunDropBytes OBJECT-TYPE
            SYNTAX Counter64
            MAX-ACCESS read-only
            STATUS current
            DESCRIPTION
                "Number of dropped bytes."
            ::= { hpnicfQoSIfTraStaRunInfoEntry 7 }

        hpnicfQoSIfTraStaRunPassPPS OBJECT-TYPE
            SYNTAX Counter64
            MAX-ACCESS read-only
            STATUS current
            DESCRIPTION
                "PPS (packets per second) of passed packets."
            ::= { hpnicfQoSIfTraStaRunInfoEntry 8 }

        hpnicfQoSIfTraStaRunPassBPS OBJECT-TYPE
            SYNTAX Counter64
            MAX-ACCESS read-only
            STATUS current
            DESCRIPTION
                "BPS (bytes per second) of passed packets."
            ::= { hpnicfQoSIfTraStaRunInfoEntry 9 }

--
-- nodes of hpnicfQoSGlobalPriorityObject
--
        hpnicfQoSGlobalPriorityObject OBJECT IDENTIFIER ::= { hpnicfIfQos2 12 }

        hpnicfQoSRemarkTcpPortPriTable OBJECT-TYPE
            SYNTAX SEQUENCE OF HpnicfQoSRemarkTcpPortPriEntry
            MAX-ACCESS not-accessible
            STATUS current
            DESCRIPTION
                "A table of remarking TCP port priority information.
                 The priority field of all packets with the specified
                 TCP port will be remarked to the configured value.
                "
            ::= { hpnicfQoSGlobalPriorityObject 1 }

        hpnicfQoSRemarkTcpPortPriEntry OBJECT-TYPE
            SYNTAX HpnicfQoSRemarkTcpPortPriEntry
            MAX-ACCESS not-accessible
            STATUS current
            DESCRIPTION
                "Remarking TCP port priority information entry."
            INDEX { hpnicfQoSRemarkTcpPortStart }
            ::= { hpnicfQoSRemarkTcpPortPriTable 1 }

        HpnicfQoSRemarkTcpPortPriEntry ::=
            SEQUENCE
            {
                hpnicfQoSRemarkTcpPortStart
                    Integer32,
                hpnicfQoSRemarkTcpPortEnd
                    Integer32,
                hpnicfQoSRemarkTcpPortType
                    INTEGER,
                hpnicfQoSRemarkTcpPortDot1p
                    Unsigned32,
                hpnicfQoSRemarkTcpPortDscp
                    Unsigned32,
                hpnicfQoSRemarkTcpPortRowStatus
                    RowStatus
            }

        hpnicfQoSRemarkTcpPortStart OBJECT-TYPE
            SYNTAX Integer32 (0..65535)
            MAX-ACCESS not-accessible
            STATUS current
            DESCRIPTION
                "Start value of TCP port range."
            ::= { hpnicfQoSRemarkTcpPortPriEntry 1 }

        hpnicfQoSRemarkTcpPortEnd OBJECT-TYPE
            SYNTAX Integer32 (0..65535)
            MAX-ACCESS read-create
            STATUS current
            DESCRIPTION
                "End value of TCP port range.
                 It cannot be less than start value.
                "
            ::= { hpnicfQoSRemarkTcpPortPriEntry 2 }

        hpnicfQoSRemarkTcpPortType OBJECT-TYPE
            SYNTAX INTEGER
            {
                ipAll(1),
                ipv4(2),
                ipv6(3)
            }
            MAX-ACCESS read-create
            STATUS current
            DESCRIPTION
                "IPv4 packet, IPv6 packet, or all IP packet."
            DEFVAL { ipAll }
            ::= { hpnicfQoSRemarkTcpPortPriEntry 3 }

        hpnicfQoSRemarkTcpPortDot1p OBJECT-TYPE
            SYNTAX Unsigned32 (0..7|255)
            MAX-ACCESS read-create
            STATUS current
            DESCRIPTION
                "Dot1p value."
            ::= { hpnicfQoSRemarkTcpPortPriEntry 4 }

        hpnicfQoSRemarkTcpPortDscp OBJECT-TYPE
            SYNTAX Unsigned32 (0..63|255)
            MAX-ACCESS read-create
            STATUS current
            DESCRIPTION
                "DSCP value."
            ::= { hpnicfQoSRemarkTcpPortPriEntry 5 }

        hpnicfQoSRemarkTcpPortRowStatus OBJECT-TYPE
            SYNTAX RowStatus
            MAX-ACCESS read-create
            STATUS current
            DESCRIPTION
                "Row status."
            ::= { hpnicfQoSRemarkTcpPortPriEntry 6 }

--hpnicfQoSRemarkUdpPortPriTable

        hpnicfQoSRemarkUdpPortPriTable OBJECT-TYPE
            SYNTAX SEQUENCE OF HpnicfQoSRemarkUdpPortPriEntry
            MAX-ACCESS not-accessible
            STATUS current
            DESCRIPTION
                "A table of remarking UDP port priority information.
                 The priority field of all packets with the specified
                 UDP port will be remarked to the configured value.
                "
            ::= { hpnicfQoSGlobalPriorityObject 2 }

        hpnicfQoSRemarkUdpPortPriEntry OBJECT-TYPE
            SYNTAX HpnicfQoSRemarkUdpPortPriEntry
            MAX-ACCESS not-accessible
            STATUS current
            DESCRIPTION
                "Remarking UDP port priority information entry."
            INDEX { hpnicfQoSRemarkUdpPortStart }
            ::= { hpnicfQoSRemarkUdpPortPriTable 1 }

        HpnicfQoSRemarkUdpPortPriEntry ::=
            SEQUENCE
            {
                hpnicfQoSRemarkUdpPortStart
                    Integer32,
                hpnicfQoSRemarkUdpPortEnd
                    Integer32,
                hpnicfQoSRemarkUdpPortType
                    INTEGER,
                hpnicfQoSRemarkUdpPortDot1p
                    Unsigned32,
                hpnicfQoSRemarkUdpPortDscp
                    Unsigned32,
                hpnicfQoSRemarkUdpPortRowStatus
                    RowStatus
            }

        hpnicfQoSRemarkUdpPortStart OBJECT-TYPE
            SYNTAX Integer32 (0..65535)
            MAX-ACCESS not-accessible
            STATUS current
            DESCRIPTION
                "Start value of UDP port range."
            ::= { hpnicfQoSRemarkUdpPortPriEntry 1 }

        hpnicfQoSRemarkUdpPortEnd OBJECT-TYPE
            SYNTAX Integer32 (0..65535)
            MAX-ACCESS read-create
            STATUS current
            DESCRIPTION
                "End value of UDP port range.
                 It cannot be less than start value.
                "
            ::= { hpnicfQoSRemarkUdpPortPriEntry 2 }

        hpnicfQoSRemarkUdpPortType OBJECT-TYPE
            SYNTAX INTEGER
            {
                ipAll(1),
                ipv4(2),
                ipv6(3)
            }
            MAX-ACCESS read-create
            STATUS current
            DESCRIPTION
                "IPv4 packet, IPv6 packet, or all IP packet."
            DEFVAL { ipAll }
            ::= { hpnicfQoSRemarkUdpPortPriEntry 3 }

        hpnicfQoSRemarkUdpPortDot1p OBJECT-TYPE
            SYNTAX Unsigned32 (0..7|255)
            MAX-ACCESS read-create
            STATUS current
            DESCRIPTION
                "Dot1p value."
            ::= { hpnicfQoSRemarkUdpPortPriEntry 4 }

        hpnicfQoSRemarkUdpPortDscp OBJECT-TYPE
            SYNTAX Unsigned32 (0..63|255)
            MAX-ACCESS read-create
            STATUS current
            DESCRIPTION
                "DSCP value."
            ::= { hpnicfQoSRemarkUdpPortPriEntry 5 }

        hpnicfQoSRemarkUdpPortRowStatus OBJECT-TYPE
            SYNTAX RowStatus
            MAX-ACCESS read-create
            STATUS current
            DESCRIPTION
                "Row status."
            ::= { hpnicfQoSRemarkUdpPortPriEntry 6 }

--hpnicfQoSRemarkIPv4AddrPriTable
        hpnicfQoSRemarkIPv4AddrPriTable OBJECT-TYPE
            SYNTAX SEQUENCE OF HpnicfQoSRemarkIPv4AddrPriEntry
            MAX-ACCESS not-accessible
            STATUS current
            DESCRIPTION
                "A table of remarking IPv4 address priority information."
            ::= { hpnicfQoSGlobalPriorityObject 3 }

        hpnicfQoSRemarkIPv4AddrPriEntry OBJECT-TYPE
            SYNTAX HpnicfQoSRemarkIPv4AddrPriEntry
            MAX-ACCESS not-accessible
            STATUS current
            DESCRIPTION
                "Remarking IPv4 address priority information entry.
                 The priority field of all IPv4 packets with the specified
                 IP address will be remarked to the configured value.
                "
            INDEX { hpnicfQoSRemarkIPv4AddrValue }
            ::= { hpnicfQoSRemarkIPv4AddrPriTable 1 }

        HpnicfQoSRemarkIPv4AddrPriEntry ::=
            SEQUENCE
            {
                hpnicfQoSRemarkIPv4AddrValue
                    IpAddress,
                hpnicfQoSRemarkIPv4AddrMask
                    IpAddress,
                hpnicfQoSRemarkIPv4AddrMaskLength
                    Unsigned32,
                hpnicfQoSRemarkIPv4AddrDot1p
                    Unsigned32,
                hpnicfQoSRemarkIPv4AddrDscp
                    Unsigned32,
                hpnicfQoSRemarkIPv4AddrRowStatus
                    RowStatus
            }

        hpnicfQoSRemarkIPv4AddrValue OBJECT-TYPE
            SYNTAX IpAddress
            MAX-ACCESS not-accessible
            STATUS current
            DESCRIPTION
                "IPv4 address."
            ::= { hpnicfQoSRemarkIPv4AddrPriEntry 1 }

        hpnicfQoSRemarkIPv4AddrMask OBJECT-TYPE
            SYNTAX IpAddress
            MAX-ACCESS read-create
            STATUS current
            DESCRIPTION
                "Mask of IPv4 address."
            ::= { hpnicfQoSRemarkIPv4AddrPriEntry 2 }

        hpnicfQoSRemarkIPv4AddrMaskLength OBJECT-TYPE
            SYNTAX Unsigned32 (1..32 |4294967295)
            MAX-ACCESS read-create
            STATUS current
            DESCRIPTION
                "Mask length of IPv4 address."
            DEFVAL { 32 }
            ::= { hpnicfQoSRemarkIPv4AddrPriEntry 3 }

        hpnicfQoSRemarkIPv4AddrDot1p OBJECT-TYPE
            SYNTAX Unsigned32 (0..7|255)
            MAX-ACCESS read-create
            STATUS current
            DESCRIPTION
                "Dot1p value."
            ::= { hpnicfQoSRemarkIPv4AddrPriEntry 4 }

        hpnicfQoSRemarkIPv4AddrDscp OBJECT-TYPE
            SYNTAX Unsigned32 (0..63|255)
            MAX-ACCESS read-create
            STATUS current
            DESCRIPTION
                "DSCP value."
            ::= { hpnicfQoSRemarkIPv4AddrPriEntry 5 }

        hpnicfQoSRemarkIPv4AddrRowStatus OBJECT-TYPE
            SYNTAX RowStatus
            MAX-ACCESS read-create
            STATUS current
            DESCRIPTION
                "Row status."
            ::= { hpnicfQoSRemarkIPv4AddrPriEntry 6 }

--hpnicfQoSRemarkIPv6AddrPriTable
        hpnicfQoSRemarkIPv6AddrPriTable OBJECT-TYPE
            SYNTAX SEQUENCE OF HpnicfQoSRemarkIPv6AddrPriEntry
            MAX-ACCESS not-accessible
            STATUS current
            DESCRIPTION
                "A table of remarking IPv6 address priority information.
                 The priority field of all IPv6 packets with the specified
                 IP address will be remarked to the configured value.
                "
            ::= { hpnicfQoSGlobalPriorityObject 4 }

        hpnicfQoSRemarkIPv6AddrPriEntry OBJECT-TYPE
            SYNTAX HpnicfQoSRemarkIPv6AddrPriEntry
            MAX-ACCESS not-accessible
            STATUS current
            DESCRIPTION
                "Remarking IPv6 address priority information entry."
            INDEX { hpnicfQoSRemarkIPv6AddrValue }
            ::= { hpnicfQoSRemarkIPv6AddrPriTable 1 }

        HpnicfQoSRemarkIPv6AddrPriEntry ::=
            SEQUENCE
            {
                hpnicfQoSRemarkIPv6AddrValue
                    InetAddressIPv6,
                hpnicfQoSRemarkIPv6AddrPrefixLength
                    InetAddressPrefixLength,
                hpnicfQoSRemarkIPv6AddrDot1p
                    Unsigned32,
                hpnicfQoSRemarkIPv6AddrDscp
                    Unsigned32,
                hpnicfQoSRemarkIPv6AddrRowStatus
                    RowStatus
            }

        hpnicfQoSRemarkIPv6AddrValue OBJECT-TYPE
            SYNTAX InetAddressIPv6
            MAX-ACCESS not-accessible
            STATUS current
            DESCRIPTION
                "IPv6 address."
            ::= { hpnicfQoSRemarkIPv6AddrPriEntry 1 }

        hpnicfQoSRemarkIPv6AddrPrefixLength OBJECT-TYPE
            SYNTAX InetAddressPrefixLength
            MAX-ACCESS read-create
            STATUS current
            DESCRIPTION
                "Prefix length of IPv6 address."
            DEFVAL { 128 }
            ::= { hpnicfQoSRemarkIPv6AddrPriEntry 2 }

        hpnicfQoSRemarkIPv6AddrDot1p OBJECT-TYPE
            SYNTAX Unsigned32 (0..7|255)
            MAX-ACCESS read-create
            STATUS current
            DESCRIPTION
                "Dot1p value."
            ::= { hpnicfQoSRemarkIPv6AddrPriEntry 3 }

        hpnicfQoSRemarkIPv6AddrDscp OBJECT-TYPE
            SYNTAX Unsigned32 (0..63|255)
            MAX-ACCESS read-create
            STATUS current
            DESCRIPTION
                "DSCP value."
            ::= { hpnicfQoSRemarkIPv6AddrPriEntry 4 }

        hpnicfQoSRemarkIPv6AddrRowStatus OBJECT-TYPE
            SYNTAX RowStatus
            MAX-ACCESS read-create
            STATUS current
            DESCRIPTION
                "Row status."
            ::= { hpnicfQoSRemarkIPv6AddrPriEntry 5 }

--hpnicfQoSRemarkProtocolPriTable
        hpnicfQoSRemarkProtocolPriTable OBJECT-TYPE
            SYNTAX SEQUENCE OF HpnicfQoSRemarkProtocolPriEntry
            MAX-ACCESS not-accessible
            STATUS current
            DESCRIPTION
                "A table of remarking layer 3 protocol priority information.
                 The 802.1p priority field of all packets of the specified
                 protocol will be remarked to the configured value.
                "
            ::= { hpnicfQoSGlobalPriorityObject 5 }

        hpnicfQoSRemarkProtocolPriEntry OBJECT-TYPE
            SYNTAX HpnicfQoSRemarkProtocolPriEntry
            MAX-ACCESS not-accessible
            STATUS current
            DESCRIPTION
                "Remarking layer 3 protocol priority information entry."
            INDEX { hpnicfQoSRemarkProtocolValue }
            ::= { hpnicfQoSRemarkProtocolPriTable 1 }

        HpnicfQoSRemarkProtocolPriEntry ::=
            SEQUENCE
            {
                hpnicfQoSRemarkProtocolValue
                    INTEGER,
                hpnicfQoSRemarkProtocolDot1p
                    Unsigned32,
                hpnicfQoSRemarkProtocolRowStatus
                    RowStatus
            }

        hpnicfQoSRemarkProtocolValue OBJECT-TYPE
            SYNTAX INTEGER
            {
                ip(1),
                ipx(2),
                arp(3),
                appletalk(4),
                sna(5),
                netbeui(6)
            }
            MAX-ACCESS not-accessible
            STATUS current
            DESCRIPTION
                "Layer 3 protocol type."
            ::= { hpnicfQoSRemarkProtocolPriEntry 1 }

        hpnicfQoSRemarkProtocolDot1p OBJECT-TYPE
            SYNTAX Unsigned32 (0..7|255)
            MAX-ACCESS read-create
            STATUS current
            DESCRIPTION
                "Dot1p value."
            ::= { hpnicfQoSRemarkProtocolPriEntry 2 }

        hpnicfQoSRemarkProtocolRowStatus OBJECT-TYPE
            SYNTAX RowStatus
            MAX-ACCESS read-create
            STATUS current
            DESCRIPTION
                "Row status."
            ::= { hpnicfQoSRemarkProtocolPriEntry 3 }

--hpnicfQoSRemarkVlanPriTable

        hpnicfQoSRemarkVlanPriTable OBJECT-TYPE
            SYNTAX SEQUENCE OF HpnicfQoSRemarkVlanPriEntry
            MAX-ACCESS not-accessible
            STATUS current
            DESCRIPTION
                "A table of remarking VLAN priority information.
                 The priority field of all packets of the specified
                 VLAN will be remarked to the configured value.
                "
            ::= { hpnicfQoSGlobalPriorityObject 6 }

        hpnicfQoSRemarkVlanPriEntry OBJECT-TYPE
            SYNTAX HpnicfQoSRemarkVlanPriEntry
            MAX-ACCESS not-accessible
            STATUS current
            DESCRIPTION
                "Remarking VLAN priority information entry."
            INDEX { hpnicfQoSRemarkVlanStart }
            ::= { hpnicfQoSRemarkVlanPriTable 1 }

        HpnicfQoSRemarkVlanPriEntry ::=
            SEQUENCE
            {
                hpnicfQoSRemarkVlanStart
                    Integer32,
                hpnicfQoSRemarkVlanEnd
                    Integer32,
                hpnicfQoSRemarkVlanDot1p
                    Unsigned32,
                hpnicfQoSRemarkVlanDscp
                    Unsigned32,
                hpnicfQoSRemarkVlanRowStatus
                    RowStatus
            }

        hpnicfQoSRemarkVlanStart OBJECT-TYPE
            SYNTAX Integer32 (1..4094)
            MAX-ACCESS not-accessible
            STATUS current
            DESCRIPTION
                "Start VLAN ID."
            ::= { hpnicfQoSRemarkVlanPriEntry 1 }

        hpnicfQoSRemarkVlanEnd OBJECT-TYPE
            SYNTAX Integer32 (1..4094)
            MAX-ACCESS read-create
            STATUS current
            DESCRIPTION
                "End VLAN ID.  It cannot be less than start value."
            ::= { hpnicfQoSRemarkVlanPriEntry 2 }

        hpnicfQoSRemarkVlanDot1p OBJECT-TYPE
            SYNTAX Unsigned32 (0..7|255)
            MAX-ACCESS read-create
            STATUS current
            DESCRIPTION
                "Dot1p value."
            ::= { hpnicfQoSRemarkVlanPriEntry 3 }

        hpnicfQoSRemarkVlanDscp OBJECT-TYPE
            SYNTAX Unsigned32 (0..63|255)
            MAX-ACCESS read-create
            STATUS current
            DESCRIPTION
                "DSCP value."
            ::= { hpnicfQoSRemarkVlanPriEntry 4 }

        hpnicfQoSRemarkVlanRowStatus OBJECT-TYPE
            SYNTAX RowStatus
            MAX-ACCESS read-create
            STATUS current
            DESCRIPTION
                "Row status."
            ::= { hpnicfQoSRemarkVlanPriEntry 5 }

--Type of service node
        hpnicfQoSTypeOfServiceObjects OBJECT IDENTIFIER
            ::= { hpnicfQoSGlobalPriorityObject 7 }

        hpnicfQoSTypeOfServiceMode OBJECT-TYPE
            SYNTAX INTEGER
            {
                disabled(1),
                ipPrecedence(2),
                dscp(3)
            }
            MAX-ACCESS read-write
            STATUS current
            DESCRIPTION
                "Global type of service.
                 The type of service is disabled by default.
                 When in ip-precedence mode, device uses ip-precedence value to
                 determine the 802.1p priority of the packet and its outbound queue.
                 When in DSCP mode, device uses DSCP value to determine
                 the 802.1p priority of the packet and its outbound queue.
                "
            DEFVAL { disabled }
            ::= { hpnicfQoSTypeOfServiceObjects 1 }

--
-- nodes of hpnicfIfQoSProcessingStatusObjects
--
        hpnicfIfQoSProcessingStatusObjects OBJECT IDENTIFIER ::= { hpnicfIfQos2 13 }

-- System status when processing

        hpnicfIfQoSProcessingStatus OBJECT-TYPE
            SYNTAX INTEGER
            {
                idle(1),
                busy(2)
            }
            MAX-ACCESS read-only
            STATUS current
            DESCRIPTION
                "This object shows the current running status of the IFQoS module.
                'busy' means a task is being executed in the IFQoS module.  It is
                highly recommended not setting or reading IFQoS MIB objects in this state.
                otherwise, an operation failure might occur.
                'idle' means no task is being executed in the IFQoS module.  In this
                state, operations on IFQoS MIB objects will be accepted and executed
                immediately."

            ::= { hpnicfIfQoSProcessingStatusObjects 1 }

END
