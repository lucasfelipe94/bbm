-- =================================================================
-- Copyright (c) 2010-2016 Hewlett-Packard Development Company, L.P.
--
-- Description: interface extension mib
-- Reference: IF-MIB
-- Version: V2.0
-- History:
--   V1.0 Created by gaolong
--     Initial version 2004-11-13
--   V1.1 2007-01-13 Modified by wanglirong
--     Added hpnicfIfStatGlobalFlowInterval and hpnicfIfSpeedStatTable
--   V1.2 Modified by chenxi
--     Added hpnicfRTParentIfTable, hpnicfRTSubIfTable, and
--     hpnicfIfLinkModeTable 2007-10-15
--   V1.3 2009-05-05 Added hpnicfIfPhysicalNumber and hpnicfIfTable
--   V1.4 2009-08-08 Added hpnicfIfMtu, hpnicfIfBandwidth, hpnicfIfDiscardPktRate,
--     and hpnicfIfExtTrapCfgTable
--   V1.5 2010-09-04 Added hpnicfIfInNUcastPkts, hpnicfIfOutNUcastPkts, and hpnicfIfStatusKeepTime by shuaixj
--   V1.6 2011-09-16 Added hpnicfIfHCFlowStatTable by xiedong
--        2011-11-04 Added hpnicfIfIsPoe by duyanbing
--   V1.7 2013-09-13 Added hpnicfIfOperStatus and hpnicfIfDownTimes by duyanbing
--   V1.8 2014-07-23 Added hpnicfIfShutDownInterval and hpnicfIfUsingTable by xiedong
--        2014-09-19 Added hpnicfIfDampeningSuppressed and hpnicfIfDampeningNotSuppressed by yinzhonghong
--   V1.9 2014-11-20 Added hpnicfIfPortTypeTable, hpnicfIfPfcStatus, and hpnicfIfPfcDot1pNoDrop by songhao
--   V2.0 2015-02-12 Added hpnicfIfPortUp, hpnicfIfPortDown by chenzhouhui
--        2015-12-10 Added hpnicfIfDescription by chenzhouhui
-- =================================================================
HPN-ICF-IF-EXT-MIB DEFINITIONS ::= BEGIN

IMPORTS
        hpnicfCommon
    FROM HPN-ICF-OID-MIB
        ifIndex, ifDescr, InterfaceIndex
    FROM IF-MIB
        Integer32, Counter64, Unsigned32, TimeTicks,
        OBJECT-TYPE, MODULE-IDENTITY, NOTIFICATION-TYPE
    FROM SNMPv2-SMI
        CounterBasedGauge64
    FROM HCNUM-TC
        DisplayString, RowStatus, TruthValue
    FROM SNMPv2-TC;

hpnicfIfExt MODULE-IDENTITY
    LAST-UPDATED "201512101000Z"
    ORGANIZATION
        ""
    CONTACT-INFO
        ""
    DESCRIPTION
        "This MIB is an extension of interface MIBs such as IF-MIB.

        This MIB is applicable to routers, switches, and other products.

        Some objects in this MIB may be used only for some specific products,
        so users should refer to the related documents to acquire more
        detailed information.
        "
    REVISION "201512101000Z"
    DESCRIPTION
        "Added hpnicfIfDescription."
    REVISION "201504020458Z"
    DESCRIPTION
        "Added hpnicfIfPortUp and hpnicfIfPortDown"
    REVISION "201411200800Z"
    DESCRIPTION
        "Added hpnicfIfPortTypeTable, hpnicfIfPfcStatus, and hpnicfIfPfcDot1pNoDrop."
    REVISION "200905061936Z"
    DESCRIPTION
        "Update this MIB module."
    REVISION "200411131936Z"        -- December 13, 2004 at 19:36 GMT
    DESCRIPTION
        "The initial revision of this MIB module."
    ::= { hpnicfCommon 40 }


--
-- Node definitions
--

-- Scalar MIB objects, which are considered as global variables
-- to all interfaces on a device, are defined in this section.
hpnicfIfExtScalarGroup OBJECT IDENTIFIER ::= { hpnicfIfExt 1 }

hpnicfIfStatGlobalFlowInterval OBJECT-TYPE
    SYNTAX      Integer32
    UNITS       "seconds"
    MAX-ACCESS  read-write
    STATUS      current
    DESCRIPTION
        "Sampling interval for in/out flow of all interfaces.
        Setting zero indicates closing the statistic function."
    ::= { hpnicfIfExtScalarGroup 1 }

hpnicfIfShutDownInterval OBJECT-TYPE
    SYNTAX      Integer32
    UNITS       "seconds"
    MAX-ACCESS  read-write
    STATUS      current
    DESCRIPTION
        "Set the port status detection timer.  The device starts a port status
        detection timer when a port is shut down by a protocol.  Once the timer
        expires, the device brings up the port so the port status reflects
        the port's physical status."
    ::= { hpnicfIfExtScalarGroup 2 }

-- =================================================================
-- All other groups are defined below.  Of course, scalar objects can
-- also be defined in a subsection, but they must be one part of
-- that subsection.

-- Note that a scalar group should be defined firstly and all
-- scalar objects are placed under that group when doing so.
hpnicfIfExtGroup OBJECT IDENTIFIER ::= { hpnicfIfExt 2 }


-- =================================================================
-- The section below describes statistics of interfaces on a device.
-- These statistics may not be included in standard MIBs.
hpnicfIfStat OBJECT IDENTIFIER ::= { hpnicfIfExtGroup 1 }

-- Define a scalar group that contains all scalar objects used for
-- interface statistics.
hpnicfIfStatScalarGroup OBJECT IDENTIFIER ::= { hpnicfIfStat 1 }

hpnicfIfStatTable OBJECT IDENTIFIER ::= { hpnicfIfStat 2 }

hpnicfIfFlowStatTable OBJECT-TYPE
    SYNTAX      SEQUENCE OF HpnicfIfFlowStatEntry
    MAX-ACCESS  not-accessible
    STATUS      current
    DESCRIPTION
        "This table contains objects to get statistic information
        of interfaces on a device."
    ::= { hpnicfIfStatTable 1 }

hpnicfIfFlowStatEntry OBJECT-TYPE
    SYNTAX      HpnicfIfFlowStatEntry
    MAX-ACCESS  not-accessible
    STATUS      current
    DESCRIPTION
        "Entry items"
    INDEX
        {
            ifIndex
        }
    ::= { hpnicfIfFlowStatTable 1 }

HpnicfIfFlowStatEntry ::= SEQUENCE
    {
        hpnicfIfStatFlowInterval    Integer32,
        hpnicfIfStatFlowInBits      Unsigned32,
        hpnicfIfStatFlowOutBits     Unsigned32,
        hpnicfIfStatFlowInPkts      Unsigned32,
        hpnicfIfStatFlowOutPkts     Unsigned32,
        hpnicfIfStatFlowInBytes     Unsigned32,
        hpnicfIfStatFlowOutBytes    Unsigned32
    }

hpnicfIfStatFlowInterval OBJECT-TYPE
    SYNTAX      Integer32
    UNITS       "seconds"
    MAX-ACCESS  read-write
    STATUS      current
    DESCRIPTION
        "Sampling interval for in/out flow of interface.
        Setting zero indicates closing this statistic function
        and objects in this table should return 0."
    ::= { hpnicfIfFlowStatEntry 1 }

hpnicfIfStatFlowInBits OBJECT-TYPE
    SYNTAX      Unsigned32
    MAX-ACCESS  read-only
    STATUS      current
    DESCRIPTION
        "In bits in the specified interval."
    ::= { hpnicfIfFlowStatEntry 2 }

hpnicfIfStatFlowOutBits OBJECT-TYPE
    SYNTAX      Unsigned32
    MAX-ACCESS  read-only
    STATUS      current
    DESCRIPTION
        "Out bits in the specified interval."
    ::= { hpnicfIfFlowStatEntry 3 }

hpnicfIfStatFlowInPkts OBJECT-TYPE
    SYNTAX      Unsigned32
    MAX-ACCESS  read-only
    STATUS      current
    DESCRIPTION
        "In packets in the specified interval."
    ::= { hpnicfIfFlowStatEntry 4 }

hpnicfIfStatFlowOutPkts OBJECT-TYPE
    SYNTAX      Unsigned32
    MAX-ACCESS  read-only
    STATUS      current
    DESCRIPTION
        "Out packets in the specified interval."
    ::= { hpnicfIfFlowStatEntry 5 }

hpnicfIfStatFlowInBytes OBJECT-TYPE
    SYNTAX      Unsigned32
    MAX-ACCESS  read-only
    STATUS      current
    DESCRIPTION
        "In bytes in the specified interval."
    ::= { hpnicfIfFlowStatEntry 6 }

hpnicfIfStatFlowOutBytes OBJECT-TYPE
    SYNTAX      Unsigned32
    MAX-ACCESS  read-only
    STATUS      current
    DESCRIPTION
        "Out bytes in the specified interval."
    ::= { hpnicfIfFlowStatEntry 7 }


-- =================================================================
hpnicfIfSpeedStatTable OBJECT-TYPE
    SYNTAX      SEQUENCE OF HpnicfIfSpeedStatEntry
    MAX-ACCESS  not-accessible
    STATUS      current
    DESCRIPTION
        "This table contains objects to get average speed information
        in the specified interval for interfaces on a device."
    ::= { hpnicfIfStatTable 2 }

hpnicfIfSpeedStatEntry OBJECT-TYPE
    SYNTAX      HpnicfIfSpeedStatEntry
    MAX-ACCESS  not-accessible
    STATUS      current
    DESCRIPTION
        "Entry items"
    INDEX
        {
            ifIndex
        }
    ::= { hpnicfIfSpeedStatTable 1 }

HpnicfIfSpeedStatEntry ::= SEQUENCE
    {
        hpnicfIfSpeedStatInterval    Integer32,
        hpnicfIfSpeedStatInPkts      Unsigned32,
        hpnicfIfSpeedStatOutPkts     Unsigned32,
        hpnicfIfSpeedStatInBytes     Unsigned32,
        hpnicfIfSpeedStatOutBytes    Unsigned32
    }

hpnicfIfSpeedStatInterval OBJECT-TYPE
    SYNTAX      Integer32
    UNITS       "seconds"
    MAX-ACCESS  read-write
    STATUS      current
    DESCRIPTION
        "Sampling interval for in/out flow of interface.
        Setting zero indicates closing this statistic function
        and objects in this table should return 0."
    ::= { hpnicfIfSpeedStatEntry 1 }

hpnicfIfSpeedStatInPkts OBJECT-TYPE
    SYNTAX      Unsigned32
    MAX-ACCESS  read-only
    STATUS      current
    DESCRIPTION
        "Average of input packets per second in the specified interval by
        hpnicfIfSpeedStatInterval."
    ::= { hpnicfIfSpeedStatEntry 2 }

hpnicfIfSpeedStatOutPkts OBJECT-TYPE
    SYNTAX      Unsigned32
    MAX-ACCESS  read-only
    STATUS      current
    DESCRIPTION
        "Average of output packets per second in the specified interval by
        hpnicfIfSpeedStatInterval."
    ::= { hpnicfIfSpeedStatEntry 3 }

hpnicfIfSpeedStatInBytes OBJECT-TYPE
    SYNTAX      Unsigned32
    MAX-ACCESS  read-only
    STATUS      current
    DESCRIPTION
        "Average of input bytes per second in the specified interval by
        hpnicfIfSpeedStatInterval."
    ::= { hpnicfIfSpeedStatEntry 4 }

hpnicfIfSpeedStatOutBytes OBJECT-TYPE
    SYNTAX      Unsigned32
    MAX-ACCESS  read-only
    STATUS      current
    DESCRIPTION
        "Average of output bytes per second in the specified interval by
        hpnicfIfSpeedStatInterval."
    ::= { hpnicfIfSpeedStatEntry 5 }

-- =================================================================
hpnicfIfHCFlowStatTable OBJECT-TYPE
    SYNTAX      SEQUENCE OF HpnicfIfHCFlowStatEntry
    MAX-ACCESS  not-accessible
    STATUS      current
    DESCRIPTION
        "This table contains objects to get statistic information
         of interfaces on a device."
    ::= { hpnicfIfStatTable 3 }

hpnicfIfHCFlowStatEntry OBJECT-TYPE
    SYNTAX      HpnicfIfHCFlowStatEntry
    MAX-ACCESS  not-accessible
    STATUS      current
    DESCRIPTION
        "Entry items"
    INDEX
        {
            ifIndex
        }
    ::= { hpnicfIfHCFlowStatTable 1 }

HpnicfIfHCFlowStatEntry ::= SEQUENCE
    {
        hpnicfIfStatFlowHCInBits      CounterBasedGauge64,
        hpnicfIfStatFlowHCOutBits     CounterBasedGauge64,
        hpnicfIfStatFlowHCInPkts      CounterBasedGauge64,
        hpnicfIfStatFlowHCOutPkts     CounterBasedGauge64,
        hpnicfIfStatFlowHCInBytes     CounterBasedGauge64,
        hpnicfIfStatFlowHCOutBytes    CounterBasedGauge64
    }

hpnicfIfStatFlowHCInBits OBJECT-TYPE
    SYNTAX      CounterBasedGauge64
    MAX-ACCESS  read-only
    STATUS      current
    DESCRIPTION
        "In bits in the specified interval.  This object is a 64-bit
         version of hpnicfIfStatFlowInBits."
    ::= { hpnicfIfHCFlowStatEntry 1 }

hpnicfIfStatFlowHCOutBits OBJECT-TYPE
    SYNTAX      CounterBasedGauge64
    MAX-ACCESS  read-only
    STATUS      current
    DESCRIPTION
        "Out bits in the specified interval.  This object is a 64-bit
         version of hpnicfIfStatFlowOutBits."
    ::= { hpnicfIfHCFlowStatEntry 2 }

hpnicfIfStatFlowHCInPkts OBJECT-TYPE
    SYNTAX      CounterBasedGauge64
    MAX-ACCESS  read-only
    STATUS      current
    DESCRIPTION
        "In packets in the specified interval.  This object is a 64-bit
         version of hpnicfIfStatFlowInPkts."
    ::= { hpnicfIfHCFlowStatEntry 3 }

hpnicfIfStatFlowHCOutPkts OBJECT-TYPE
    SYNTAX      CounterBasedGauge64
    MAX-ACCESS  read-only
    STATUS      current
    DESCRIPTION
        "Out packets in the specified interval.  This object is a 64-bit
         version of hpnicfIfStatFlowOutPkts."
    ::= { hpnicfIfHCFlowStatEntry 4 }

hpnicfIfStatFlowHCInBytes OBJECT-TYPE
    SYNTAX      CounterBasedGauge64
    MAX-ACCESS  read-only
    STATUS      current
    DESCRIPTION
        "In bytes in the specified interval.  This object is a 64-bit
         version of hpnicfIfStatFlowInBytes."
    ::= { hpnicfIfHCFlowStatEntry 5 }

hpnicfIfStatFlowHCOutBytes OBJECT-TYPE
    SYNTAX      CounterBasedGauge64
    MAX-ACCESS  read-only
    STATUS      current
    DESCRIPTION
        "Out bytes in the specified interval.  This object is a 64-bit
         version of hpnicfIfStatFlowOutBytes."
    ::= { hpnicfIfHCFlowStatEntry 6 }

-- =================================================================

hpnicfIfControl OBJECT IDENTIFIER ::= { hpnicfIfExtGroup 2 }

hpnicfRTParentIfTable OBJECT-TYPE
    SYNTAX      SEQUENCE OF HpnicfRTParentIfEntry
    MAX-ACCESS  not-accessible
    STATUS      current
    DESCRIPTION
        "This table contains all interfaces that can create subinterfaces."
    ::= { hpnicfIfControl  1 }

hpnicfRTParentIfEntry OBJECT-TYPE
    SYNTAX      HpnicfRTParentIfEntry
    MAX-ACCESS  not-accessible
    STATUS      current
    DESCRIPTION
        "This entry describes an interface that can create subinterfaces."
    INDEX
        {
            hpnicfRTParentIfIndex
        }
    ::= { hpnicfRTParentIfTable 1}

HpnicfRTParentIfEntry    ::= SEQUENCE
    {
        hpnicfRTParentIfIndex      Integer32,
        hpnicfRTMinSubIfOrdinal    Integer32,
        hpnicfRTMaxSubIfOrdinal    Integer32
    }

hpnicfRTParentIfIndex OBJECT-TYPE
    SYNTAX      Integer32(1..2147483647)
    MAX-ACCESS  not-accessible
    STATUS      current
    DESCRIPTION
        "The index of the interface that can create subinterfaces.  The value
        is the same as the ifIndex value for this interface."
    ::= { hpnicfRTParentIfEntry 1 }

hpnicfRTMinSubIfOrdinal OBJECT-TYPE
    SYNTAX      Integer32
    MAX-ACCESS  read-only
    STATUS      current
    DESCRIPTION
        "The min ordinal of the subinterface."
    ::= { hpnicfRTParentIfEntry 2 }

hpnicfRTMaxSubIfOrdinal OBJECT-TYPE
    SYNTAX      Integer32
    MAX-ACCESS  read-only
    STATUS      current
    DESCRIPTION
        "The max ordinal of the subinterface."
    ::= { hpnicfRTParentIfEntry 3 }

-- =================================================================

hpnicfRTSubIfTable OBJECT-TYPE
    SYNTAX      SEQUENCE OF HpnicfRTSubIfEntry
    MAX-ACCESS  not-accessible
    STATUS      current
    DESCRIPTION
        "This table contains objects to create or delete subinterfaces.
        To create a subinterface, a valid parent interface must be
        specified by hpnicfRTSubIfParentIfIndex, and hpnicfRTSubIfOrdinal
        must be in the range between hpnicfRTMinSubIfOrdinal and
        hpnicfRTMaxSubIfOrdinal of the parent interface from
        hpnicfRTParentIfTable.

        Subinterfaces are logical virtual interfaces configured on a
        main interface.  The main interface can be either a physical
        interface (such as a Layer 3 Ethernet interface) or a logical
        interface (such as an MFR interface).  The subinterfaces on a
        main interface share the physical layer parameters of the main
        interface but can have link layer and network layer parameters
        of their own.  Disabling or enabling a subinterface doesn't
        affect the main interface, but the main interface status change
        affects the subinterfaces.  The subinterfaces can't operate
        correctly unless the main interface is connected.
        Creating multiple subinterfaces on a single interface
        enables you to plan network in a more flexible way.

        You can create subinterfaces for the following physical
        interfaces:
        Ethernet interface.  An Ethernet subinterface associated with no
        VLAN supports only IPX, while an Ethernet subinterface associated
        with a VLAN supports both IP and IPX.
        WAN interfaces with their data link layer protocols being frame
        relay, whose subinterfaces support IP and IPX.
        WAN interfaces with their data link layer protocols being X.25,
        whose subinterfaces support IP and IPX.
        ATM interface, whose subinterfaces support only IP."
    ::= { hpnicfIfControl  2 }

hpnicfRTSubIfEntry OBJECT-TYPE
    SYNTAX      HpnicfRTSubIfEntry
    MAX-ACCESS  not-accessible
    STATUS      current
    DESCRIPTION "The hpnicfRTSubIfTable entry items"
    INDEX
        {
            hpnicfRTSubIfParentIfIndex,
            hpnicfRTSubIfOrdinal
        }
    ::= { hpnicfRTSubIfTable 1}

HpnicfRTSubIfEntry    ::= SEQUENCE
    {
        hpnicfRTSubIfParentIfIndex    Integer32,
        hpnicfRTSubIfOrdinal          Integer32,
        hpnicfRTSubIfSubIfIndex       Integer32,
        hpnicfRTSubIfSubIfDesc        DisplayString,
        hpnicfRTSubIfRowStatus        RowStatus
    }

hpnicfRTSubIfParentIfIndex OBJECT-TYPE
    SYNTAX      Integer32(1..2147483647)
    MAX-ACCESS  not-accessible
    STATUS      current
    DESCRIPTION
        "The parent interface index.  The value should be the same as
        hpnicfRTParentIfIndex."
    ::= { hpnicfRTSubIfEntry 1 }

hpnicfRTSubIfOrdinal OBJECT-TYPE
    SYNTAX      Integer32(1..2147483647)
    MAX-ACCESS  not-accessible
    STATUS      current
    DESCRIPTION
        "The ordinal of the subinterface.  It should between
        hpnicfRTMinSubIfOrdinal and hpnicfRTMaxSubIfOrdinal of the parent
        interface."
    ::= { hpnicfRTSubIfEntry 2 }

hpnicfRTSubIfSubIfIndex OBJECT-TYPE
    SYNTAX      Integer32
    MAX-ACCESS  read-only
    STATUS      current
    DESCRIPTION
        "The ifIndex value of the subinterface"
    ::= { hpnicfRTSubIfEntry 3 }

hpnicfRTSubIfSubIfDesc OBJECT-TYPE
    SYNTAX      DisplayString(SIZE(0..255))
    MAX-ACCESS  read-only
    STATUS      current
    DESCRIPTION
        "The name of the interface"
    ::= { hpnicfRTSubIfEntry 4 }

hpnicfRTSubIfRowStatus OBJECT-TYPE
    SYNTAX      RowStatus
    MAX-ACCESS  read-create
    STATUS      current
    DESCRIPTION
        "Operation status."
    ::= { hpnicfRTSubIfEntry 5 }

-- =================================================================
hpnicfIfLinkModeTable OBJECT-TYPE
    SYNTAX      SEQUENCE OF HpnicfIfLinkModeEntry
    MAX-ACCESS  not-accessible
    STATUS      current
    DESCRIPTION
        "This table contains objects to get or set the link mode of an
        interface.
        According to the layer at which the device processes received
        data packets, Ethernet interfaces can operate in bridge or route
        mode."
    ::= { hpnicfIfControl  3 }

hpnicfIfLinkModeEntry OBJECT-TYPE
    SYNTAX      HpnicfIfLinkModeEntry
    MAX-ACCESS  not-accessible
    STATUS      current
    DESCRIPTION "The interface link mode table entry"
    INDEX
        {
            hpnicfIfLinkModeIndex
        }
    ::= { hpnicfIfLinkModeTable 1}

HpnicfIfLinkModeEntry    ::= SEQUENCE
    {
        hpnicfIfLinkModeIndex            Integer32,
        hpnicfIfLinkMode                 INTEGER,
        hpnicfIfLinkModeSwitchSupport    TruthValue
    }

hpnicfIfLinkModeIndex OBJECT-TYPE
    SYNTAX      Integer32(1..2147483647)
    MAX-ACCESS  not-accessible
    STATUS      current
    DESCRIPTION
        "The value is the same as ifIndex."
    ::= { hpnicfIfLinkModeEntry 1 }


hpnicfIfLinkMode OBJECT-TYPE
    SYNTAX      INTEGER
        {
            bridgeMode(1),
            routeMode(2)
        }
    MAX-ACCESS  read-write
    STATUS      current
    DESCRIPTION
        "The current link mode of the interface.
        If hpnicfIfLinkModeSwitchSupport is true, writing to the object can
        change the link mode of the interface."
    ::= { hpnicfIfLinkModeEntry 2 }

hpnicfIfLinkModeSwitchSupport OBJECT-TYPE
    SYNTAX      TruthValue
    MAX-ACCESS  read-only
    STATUS      current
    DESCRIPTION
        "Whether the interface supports link mode switching.
        If this object is true, the interface can operate in either
        bridge mode or route mode.  Otherwise the interfaces can operate
        only in bridge or route mode."
    ::= { hpnicfIfLinkModeEntry 3 }

-- =================================================================
hpnicfIfPortTypeTable OBJECT-TYPE
    SYNTAX      SEQUENCE OF HpnicfIfPortTypeEntry
    MAX-ACCESS  not-accessible
    STATUS      current
    DESCRIPTION
        "This table contains objects to get or set the port type
        of an interface."
    ::= { hpnicfIfControl  4 }

hpnicfIfPortTypeEntry OBJECT-TYPE
    SYNTAX      HpnicfIfPortTypeEntry
    MAX-ACCESS  not-accessible
    STATUS      current
    DESCRIPTION "The interface port type table entry."
    INDEX
        {
            hpnicfIfPortTypeIndex
        }
    ::= { hpnicfIfPortTypeTable 1}

HpnicfIfPortTypeEntry    ::= SEQUENCE
    {
        hpnicfIfPortTypeIndex            InterfaceIndex,
        hpnicfIfPortType                 INTEGER
    }

hpnicfIfPortTypeIndex OBJECT-TYPE
    SYNTAX      InterfaceIndex
    MAX-ACCESS  not-accessible
    STATUS      current
    DESCRIPTION
        "The value is the same as ifIndex."
    ::= { hpnicfIfPortTypeEntry 1 }

hpnicfIfPortType OBJECT-TYPE
    SYNTAX      INTEGER
        {
            other(1),
            ethernet(2),
            fc(3)
        }
    MAX-ACCESS  read-write
    STATUS      current
    DESCRIPTION
        "The current port type of the interface.
        Don't set the port type to other for an interface."
    ::= { hpnicfIfPortTypeEntry 2 }


hpnicfIfInterfaces OBJECT IDENTIFIER ::= { hpnicfIfExtGroup 3 }

hpnicfIfPhysicalNumber OBJECT-TYPE
    SYNTAX      Integer32
    MAX-ACCESS  read-only
    STATUS      current
    DESCRIPTION
        "Represents the number of physical interfaces on the device."
    ::= { hpnicfIfInterfaces 1 }

hpnicfIfTable OBJECT-TYPE
    SYNTAX      SEQUENCE OF HpnicfIfEntry
    MAX-ACCESS  not-accessible
    STATUS      current
    DESCRIPTION
        "A list of interface entries.  The number of entries is given by
         the value of IfNumber."
    ::= { hpnicfIfInterfaces 2 }

hpnicfIfEntry OBJECT-TYPE
    SYNTAX      HpnicfIfEntry
    MAX-ACCESS  not-accessible
    STATUS      current
    DESCRIPTION
        "An entry containing management information applicable to a
         particular interface."
    INDEX
        {
            ifIndex
        }
    ::= { hpnicfIfTable 1 }

HpnicfIfEntry ::= SEQUENCE
    {
        hpnicfIfUpDownTimes      Integer32,
        hpnicfIfMtu              Integer32,
        hpnicfIfBandwidthRate    Integer32,
        hpnicfIfDiscardPktRate   Integer32,
        hpnicfIfStatusKeepTime   TimeTicks,
        hpnicfIfInNUcastPkts     Counter64,
        hpnicfIfOutNUcastPkts    Counter64,
        hpnicfIfIsPoe            TruthValue,
        hpnicfIfOperStatus       INTEGER,
        hpnicfIfDownTimes        Integer32,
        hpnicfIfPfcStatus        INTEGER,
        hpnicfIfPfcDot1pNoDrop   BITS,
        hpnicfIfDescription      DisplayString
    }

hpnicfIfUpDownTimes OBJECT-TYPE
    SYNTAX      Integer32
    MAX-ACCESS  read-only
    STATUS      current
    DESCRIPTION
        "The interface's up/down times, since the device was initialized."
    ::= { hpnicfIfEntry 1 }

hpnicfIfMtu OBJECT-TYPE
    SYNTAX      Integer32
    MAX-ACCESS  read-write
    STATUS      current
    DESCRIPTION
        "The size of the largest datagram that can be sent or received on the
        interface, specified in octets.  For interfaces that are used for
        transmitting network datagram, this is the size of the largest network
        datagram that can be sent on the interfaces."
    ::= { hpnicfIfEntry 2 }

hpnicfIfBandwidthRate OBJECT-TYPE
    SYNTAX      Integer32(0..100)
    MAX-ACCESS  read-only
    STATUS      current
    DESCRIPTION
        "The rate of the bandwidth for an interface."
    ::= { hpnicfIfEntry 3 }

hpnicfIfDiscardPktRate OBJECT-TYPE
    SYNTAX      Integer32(0..100)
    MAX-ACCESS  read-only
    STATUS      current
    DESCRIPTION
        "The rate of the discarded packets for an interface."
    ::= { hpnicfIfEntry 4 }

hpnicfIfStatusKeepTime OBJECT-TYPE
    SYNTAX      TimeTicks
    MAX-ACCESS  read-only
    STATUS      current
    DESCRIPTION
        "The time since the interface
        entered its current operational state."
    ::= { hpnicfIfEntry 5 }

hpnicfIfInNUcastPkts OBJECT-TYPE
    SYNTAX      Counter64
    MAX-ACCESS  read-only
    STATUS      current
    DESCRIPTION
        "The number of non-unicast (i.e., subnetwork-
        broadcast or subnetwork-multicast) packets
        delivered to a higher-layer protocol."
    ::= { hpnicfIfEntry 6 }

hpnicfIfOutNUcastPkts OBJECT-TYPE
    SYNTAX      Counter64
    MAX-ACCESS  read-only
    STATUS      current
    DESCRIPTION
        "The total number of packets that higher-level
        protocols requested be transmitted to a non-
        unicast (i.e., a subnetwork-broadcast or
        subnetwork-multicast) address."
    ::= { hpnicfIfEntry 7 }

hpnicfIfIsPoe OBJECT-TYPE
    SYNTAX      TruthValue
    MAX-ACCESS  read-only
    STATUS      current
    DESCRIPTION
        "Whether the interface supports PoE."
    ::= { hpnicfIfEntry 8 }

hpnicfIfOperStatus OBJECT-TYPE
    SYNTAX  INTEGER {
                up(1),        -- ready to forward packets
                down(2),
                testing(3),   -- in a test mode
                admindown(4)  -- shut down by administrator
            }
    MAX-ACCESS  read-only
    STATUS      current
    DESCRIPTION
            "Current status of the interface.  In testing state,
            no operational packets can be forwarded.  If ifAdminStatus
            is down, hpnicfIfOperStatus should be admindown.  If
            ifAdminStatus is changed to up, hpnicfIfOperStatus should
            change to up if the interface is ready to send and receive
            network traffic; otherwise, it should stay in down state."
    ::= { hpnicfIfEntry 9 }

hpnicfIfDownTimes OBJECT-TYPE
    SYNTAX      Integer32
    MAX-ACCESS  read-only
    STATUS      current
    DESCRIPTION
        "Number of times the interface went down, since the device was initialized."
    ::= { hpnicfIfEntry 10 }

hpnicfIfPfcStatus OBJECT-TYPE
    SYNTAX      INTEGER
        {
            enable(1),
            disable(2),
            auto(3)
        }
    MAX-ACCESS  read-write
    STATUS      current
    DESCRIPTION
        "PFC (Priority-based Flow Control) status.
         Forcibly enable PFC by enable(1).
         Disable PFC by disable(2).
         Set PFC to auto mode by auto(3).
               In auto mode, the local end automatically negotiates
               the PFC status with its peer.
         When congestion occurs in the network, the local device notifies
         the peer to stop sending packets carrying the specified 802.1p
         priority if all of the following conditions exist:
         1. Both the local end and the remote end have PFC enabled.
         2. Both the local end and the remote end have the dot1p list specified
         by hpnicfIfPfcDot1pNoDrop.
         3. The specified 802.1p priority is in the dot1p list of hpnicfIfPfcDot1pNoDrop.
         4. The local end receives a packet carrying the specified 802.1p priority."
    DEFVAL { disable }
    ::= { hpnicfIfEntry 11 }

hpnicfIfPfcDot1pNoDrop OBJECT-TYPE
    SYNTAX      BITS { pri0(0), pri1(1), pri2(2), pri3(3), pri4(4), pri5(5), pri6(6), pri7(7) }
    MAX-ACCESS  read-write
    STATUS      current
    DESCRIPTION
        "PFC (Priority-based Flow Control) dot1q list,
        bit 0 through bit 7 corresponding to priority 0 through priority 7.
        See hpnicfIfPfcStatus."
    DEFVAL{ { } }
    ::= { hpnicfIfEntry 12 }

hpnicfIfDescription OBJECT-TYPE
    SYNTAX      DisplayString (SIZE(0..255))
    MAX-ACCESS  read-write
    STATUS      current
    DESCRIPTION
        "This object is also an 'alias' name for the interface specified by a
        network manager, like the object of ifAlias.  However, the size of
        this object is larger than ifAlias.  When this object is set to a
        string of more than 64 characters, only the first 64 characters of the
        object are read for the IfAlias object."
    ::= { hpnicfIfEntry 13 }

hpnicfIfUsingTable OBJECT-TYPE
    SYNTAX      SEQUENCE OF HpnicfIfUsingEntry
    MAX-ACCESS  not-accessible
    STATUS      current
    DESCRIPTION
        "A table containing management information applicable to splitting
       interfaces.  To improve port density, reduce costs, and improve network
       flexibility, a high-bandwidth interface can be split into multiple
       low-bandwidth breakout interfaces, and the breakout interfaces can be
       combined into a higher-bandwidth interface.
       For example, a 40-GE interface can be split into four 10-GE breakout
       interfaces.  After the operation takes effect on a 40-GE interface, the
       system deletes the 40-GE interface and creates four 10-GE breakout
       interfaces."
    ::= { hpnicfIfInterfaces 3 }

hpnicfIfUsingEntry OBJECT-TYPE
    SYNTAX      HpnicfIfUsingEntry
    MAX-ACCESS  not-accessible
    STATUS      current
    DESCRIPTION
        "An entry of hpnicfIfUsingTable."
    INDEX { hpnicfIfUsingIndex }
    ::= { hpnicfIfUsingTable 1 }

HpnicfIfUsingEntry ::= SEQUENCE
    {
        hpnicfIfUsingIndex              Integer32,
        hpnicfIfUsingSupportType        Integer32,
        hpnicfIfUsingType               INTEGER,
        hpnicfIfUsingStatus             INTEGER
    }

hpnicfIfUsingIndex OBJECT-TYPE
    SYNTAX      Integer32(1..2147483647)
    MAX-ACCESS  not-accessible
    STATUS      current
    DESCRIPTION
        "Index of an interface that can be split into multiple low-bandwidth
        breakout interfaces or be restored to a high-bandwidth interface."
    ::= { hpnicfIfUsingEntry 1 }

hpnicfIfUsingSupportType OBJECT-TYPE
    SYNTAX      Integer32
    MAX-ACCESS  read-only
    STATUS      current
    DESCRIPTION
        "This object specifies the port type which can be split into or restored to.
        From lowest bit, each bit corresponds to a port type ('10GE', '20GE',
        '40GE', '100GE').
        For example, value 3 means this object can be split into 10GE or 20GE,
        value 4 means this object can be split into 40GE, or can be restored to
        40GE."
    ::= { hpnicfIfUsingEntry 2 }

hpnicfIfUsingType OBJECT-TYPE
    SYNTAX  INTEGER {
                noUsing(0),
                using10GE(1),
                using20GE(2),
                using40GE(3),
                using100GE(4)
             }
    MAX-ACCESS  read-write
    STATUS      current
    DESCRIPTION
        "This object specifies the port type that can be split into or restored to.

        After this object is set to a non-zero value, the operation returns
        success in the following cases:
        1.  The original instance still exists and is read as a non-zero value.
            In this case, object hpnicfIfUsingStatus change to needReboot(1),
            which means that you need to reboot the line card (for distributed
            devices) or device (for centralized devices) where the port is
            located to make the operation take effect.
            Set this object to noUsing(0) for cancelling the operation.
        2.  The operation takes effect immediately.
        Original instance is deleted and new instance is created while the
        operation takes effect."
    ::= { hpnicfIfUsingEntry 3 }

hpnicfIfUsingStatus OBJECT-TYPE
    SYNTAX  INTEGER {
                noUsing(0),
                needReboot(1)
             }
    MAX-ACCESS  read-only
    STATUS      current
    DESCRIPTION
        " After object hpnicfIfUsingType is set to a non-zero value, the value
         for this object is needReboot(1) until you reboot the line card (for
         distributed devices) or device (for centralized devices) where the
         port is located."
    ::= { hpnicfIfUsingEntry 4 }

--
-- Notification definitions
--
-- =================================================================
-- Traps are defined below.

hpnicfIfExtTrap OBJECT IDENTIFIER ::= { hpnicfIfExt 3 }
hpnicfIfExtTrapPrex OBJECT IDENTIFIER ::= { hpnicfIfExtTrap 0 }
-- All trap definitions should be placed under this object.

hpnicfIfBandwidthUsageHigh NOTIFICATION-TYPE
    OBJECTS
        {
            ifDescr,
            hpnicfIfBandwidthRate,
            hpnicfIfBandwidthUpperLimit
        }
    STATUS current
    DESCRIPTION
        "The notification is generated when the rate of the bandwidth for the
         interface exceeds the upper limit."
    ::= { hpnicfIfExtTrapPrex 1 }

hpnicfIfDiscardPktRateHigh NOTIFICATION-TYPE
    OBJECTS
        {
            ifDescr,
            hpnicfIfDiscardPktRate,
            hpnicfIfDiscardPktRateUpperLimit
        }
    STATUS current
    DESCRIPTION
        "The notification is generated when the rate of the discarded packets
         for the interface exceeds the upper limit."
    ::= { hpnicfIfExtTrapPrex 2 }

hpnicfIfDampeningSuppressed NOTIFICATION-TYPE
    OBJECTS
        {
            ifIndex,
            ifDescr
        }
    STATUS current
    DESCRIPTION
        "The notification is generated when the interface is suppressed
         via dampening."
    ::= { hpnicfIfExtTrapPrex 3 }

hpnicfIfDampeningNotSuppressed NOTIFICATION-TYPE
    OBJECTS
        {
            ifIndex,
            ifDescr
        }
    STATUS current
    DESCRIPTION
        "The notification is generated when the interface is resumed to
         not suppressed via dampening."
    ::= { hpnicfIfExtTrapPrex 4 }

hpnicfIfPortUp NOTIFICATION-TYPE
    OBJECTS
        {
            ifIndex,
            ifDescr
        }
    STATUS current
    DESCRIPTION
        "The notification is generated when physical state of the interface changes to up."
    ::= { hpnicfIfExtTrapPrex 5 }

hpnicfIfPortDown NOTIFICATION-TYPE
    OBJECTS
        {
            ifIndex,
            ifDescr
        }
    STATUS current
    DESCRIPTION
        "The notification is generated when physical state of the interface changes to down."
    ::= { hpnicfIfExtTrapPrex 6 }

hpnicfIfExtTrapObject OBJECT IDENTIFIER ::= { hpnicfIfExtTrap 1 }

hpnicfIfExtTrapCfgTable OBJECT-TYPE
    SYNTAX      SEQUENCE OF HpnicfIfExtTrapCfgEntry
    MAX-ACCESS  not-accessible
    STATUS      current
    DESCRIPTION
        "The trap configuration table."
    ::= { hpnicfIfExtTrapObject 1 }

hpnicfIfExtTrapCfgEntry OBJECT-TYPE
    SYNTAX      HpnicfIfExtTrapCfgEntry
    MAX-ACCESS  not-accessible
    STATUS      current
    DESCRIPTION
        "An entry for this table."
    INDEX
        {
            ifIndex
        }
    ::= { hpnicfIfExtTrapCfgTable 1 }

HpnicfIfExtTrapCfgEntry ::= SEQUENCE
    {
        hpnicfIfBandwidthUpperLimit      Integer32,
        hpnicfIfDiscardPktRateUpperLimit Integer32
    }

hpnicfIfBandwidthUpperLimit OBJECT-TYPE
    SYNTAX      Integer32(1..100)
    MAX-ACCESS  read-write
    STATUS      current
    DESCRIPTION
        "The rate of the bandwidth upper limit for an interface."
    ::= { hpnicfIfExtTrapCfgEntry 1 }

hpnicfIfDiscardPktRateUpperLimit OBJECT-TYPE
    SYNTAX      Integer32(1..100)
    MAX-ACCESS  read-write
    STATUS      current
    DESCRIPTION
        "The rate of the discarded packets upper limit for an interface."
    ::= { hpnicfIfExtTrapCfgEntry 2 }

END
